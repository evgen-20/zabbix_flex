-- ********************************************************************************
-- File         : cme.mib
-- Description  : Chassis Management Module (CMM) MIB for SNMP
-- Version      : v23
-- Date         : February 2015
-- Copyright (c) 2014 IBM All Rights Reserved.
-- Copyright (c) 2015 Lenovo All Rights Reserved.
--
-- The CMM MIB (cme.mib) is written in SNMPv1 SMI format,
-- which does not include a SYNTAX definition for an unsigned data type.
-- This data type, however, is important and is used for objects
-- in this MIB.
--
-- Some management tools, MIB browsers, and MIB compiler tools will raise
-- errors when encountering this Unsigned32 SYNTAX. To alleviate these
-- errors, the MIB file may be updated using one of these methods:
--
-- 1) Define the Unsigned32 TEXTUAL-CONVENTION
--
--          Unsigned32 ::= TEXTUAL-CONVENTION
--                         STATUS       current
--                         DESCRIPTION
--                         Unsigned integer data type
--                         SYNTAX       INTEGER (0..4294967295)
--
-- 2) Define an Unsigned32 integer range
--
--          Unsigned32 ::=  INTEGER (0..4294967295)
--
-- 3) Define an alias for Unsigned32 integer range and then update the
--    usage of it in the MIB file:
--
--          AliasUnsigned32 ::=  INTEGER (0..4294967295)
--
--          SYNTAX  AliasUnsigned32   // For example
--
-- 4) Add the Unsigned32 line to the IMPORTS list:
--
--     IMPORTS                                                                  
--        OBJECT-TYPE        FROM RFC-1212                                
--        enterprises        FROM RFC1155-SMI                              
--        IpAddress          FROM RFC1155-SMI
--        Unsigned32         FROM SNMPv2-SMI
--        TRAP-TYPE          FROM RFC-1215;
--
-- ********************************************************************************

CME-MIB DEFINITIONS ::= BEGIN

        IMPORTS
            OBJECT-TYPE                          FROM RFC-1212
            enterprises                          FROM RFC1155-SMI
            IpAddress                            FROM RFC1155-SMI
            TRAP-TYPE                            FROM RFC-1215;

            -- textual conventions

            InetAddressIPv6 ::= TEXTUAL-CONVENTION
                        DISPLAY-HINT "2x:2x:2x:2x:2x:2x:2x:2x"
                        STATUS       current
                        DESCRIPTION
                        "Represents an IPv6 network address. Since MIB browsers
                         may require different formats, the address is
                         expected to be the 16 byte address in network-byte order,
                         and shortened formats such as 0::0 are not accepted in SET
                         operations. Two common examples are:

                         The NetSNMP command line will accept SET requests like:
                           snmpset -v1 -cprivate <host> s 2001:00:00:00:FFFF:CCC4:BBB2:AAA6

                         Other MIB browsers may require the SET request value to be formatted as:
                           # 0x20 0x01 0x00 0x00 0x00 0x00 0x00 0x00 0xFF 0xFF 0xCC 0xC4 0xBB 0xB2 0xAA 0xA6"
                        SYNTAX       OCTET STRING (SIZE (16)) 

            EntryStatus ::= INTEGER
                         { valid(1),
                           createRequest(2),
                           underCreation(3),
                           invalid(4)
                         }

              -- The status of a table entry.
              --
              -- Setting this object to the value invalid(4) has the
              -- effect of invalidating the corresponding entry.
              -- That is, it effectively disassociates the mapping
              -- identified with said entry.
              -- It is an implementation-specific matter as to whether
              -- the agent removes an invalidated entry from the table.
              -- Accordingly, management stations must be prepared to
              -- receive tabular information from agents that corresponds
              -- to entries currently not in use.  Proper
              -- interpretation of such entries requires examination
              -- of the relevant EntryStatus object.
              --
              -- An existing instance of this object cannot be set to
              -- createRequest(2).  This object may only be set to
              -- createRequest(2) when this instance is created.  When
              -- this object is created, the agent may wish to create
              -- supplemental object instances to complete a conceptual
              -- row in this table.  Immediately after completing the
              -- create operation, the agent must set this object to
              -- underCreation(3).
              --
              -- Entries shall exist in the underCreation(3) state until

              -- the management station is finished configuring the
              -- entry and sets this object to valid(1) or aborts,
              -- setting this object to invalid(4).  If the agent
              -- determines that an entry has been in the
              -- underCreation(3) state for an abnormally long time,
              -- it may decide that the management station has
              -- crashed.  If the agent makes this decision,
              -- it may set this object to invalid(4) to reclaim the
              -- entry.  A prudent agent will understand that the
              -- management station may need to wait for human input
              -- and will allow for that possibility in its
              -- determination of this abnormally long period.

        -- Enterprise group
        ibm         OBJECT IDENTIFIER ::=   { enterprises 2 }

        -- Products group
        ibmAgents      OBJECT IDENTIFIER ::=   { ibm 3 }

        -- Advanced System Management Support Processor (SP) agent group
        netfinitySupportProcessorAgent OBJECT IDENTIFIER ::= { ibmAgents 51 }

        -- Management Module (MM)
        bladeCenterSnmpMIB     OBJECT IDENTIFIER ::= { netfinitySupportProcessorAgent 2 }

  -- This group of objects provides the various environmental monitors for 
  -- chassis
  monitors OBJECT IDENTIFIER ::= { bladeCenterSnmpMIB 2 }

  -- This group of objects provides the error log information
  errorLogs OBJECT IDENTIFIER ::= { bladeCenterSnmpMIB 3 }

  -- This group of objects provides configuration functions for the CME
  configureSP     OBJECT IDENTIFIER ::= { bladeCenterSnmpMIB 4 }

  -- This group of objects provides system management functions for the telco chassis
  telcoManagement  OBJECT IDENTIFIER ::= { bladeCenterSnmpMIB 5 }

  -- This group of objects provides functions to boot the CME
  restartReset      OBJECT IDENTIFIER ::= { bladeCenterSnmpMIB 7 }

  -- This group of objects provides information specific to various
  -- components in the chassis
  components OBJECT IDENTIFIER ::= { bladeCenterSnmpMIB 22 }

  -- This group of objects provides information specific to service
  service OBJECT IDENTIFIER ::= { bladeCenterSnmpMIB 23 }

  -- This group of objects provides information specific to scaling blades
  scaling OBJECT IDENTIFIER ::= { bladeCenterSnmpMIB 24 }

    -- ********************************************************************************
    -- Temperature
    -- ********************************************************************************
    temperature OBJECT IDENTIFIER ::= { monitors 1 }

    -- ********************************************************************************
    -- Internal Temperature  (was planarTemp)
    -- ********************************************************************************
     internalTemp OBJECT IDENTIFIER ::= { temperature 1 }

     cmmTemp      OBJECT-TYPE
                   SYNTAX  OCTET STRING
                   ACCESS  read-only
                   STATUS  deprecated
                   DESCRIPTION
                   "This field is deprecated. The return value of this field is the same as rearLEDCardTemp.
		   Chassis management module temperature in degrees centigrade(C).
                   An octet string expressed as 'sddd.dd Centigrade' where:
                   s is the sign ('-' for negative or blank space for positive)
                   d is a decimal digit or blank space for leading zeroes.
                   The string 'Not Readable!' indicates that the given monitor
                   is not supported on this system."
                   ::= { internalTemp 2 }

    -- ********************************************************************************
    -- System Ambient Temperature  (was ambient frontPanelTemp)
    -- ********************************************************************************
     ambientTemp OBJECT IDENTIFIER ::= { temperature 5 }

     rearLEDCardTempAvg    OBJECT-TYPE
                   SYNTAX  OCTET STRING
                   ACCESS  read-only
                   STATUS  mandatory
                   DESCRIPTION
                   "The average rear LED card temperature in degrees centigrade(C).
                   This is surrounding temperature where the system is installed.
                   An octet string expressed as 'sddd.dd Centigrade' where:
                   s is the sign ('-' for negative or blank space for positive)
                   d is a decimal digit or blank space for a leading zero.
                   The string 'Not Readable!' indicates that the given monitor
                   is not supported on this system."
                   ::= { ambientTemp 1 }

     rearLEDCardTempMin    OBJECT-TYPE
                   SYNTAX  OCTET STRING
                   ACCESS  read-only
                   STATUS  mandatory
                   DESCRIPTION
                   "The minimum rear LED card temperature in degrees centigrade(C).
                   This is surrounding temperature where the system is installed.
                   An octet string expressed as 'sddd.dd Centigrade' where:
                   s is the sign ('-' for negative or blank space for positive)
                   d is a decimal digit or blank space for a leading zero.
                   The string 'Not Readable!' indicates that the given monitor
                   is not supported on this system."
                   ::= { ambientTemp 2 }

     rearLEDCardTempMax    OBJECT-TYPE
                   SYNTAX  OCTET STRING
                   ACCESS  read-only
                   STATUS  mandatory
                   DESCRIPTION
                   "The maximum rear LED card temperature in degrees centigrade(C).
                   This is surrounding temperature where the system is installed.
                   An octet string expressed as 'sddd.dd Centigrade' where:
                   s is the sign ('-' for negative or blank space for positive)
                   d is a decimal digit or blank space for a leading zero.
                   The string 'Not Readable!' indicates that the given monitor
                   is not supported on this system."
                   ::= { ambientTemp 3 }

    -- ********************************************************************************
    -- System monitor Temperature
    -- ********************************************************************************
     monitorTemp OBJECT IDENTIFIER ::= { temperature 9 }

     hotAirRecircMonitoring OBJECT-TYPE
                   SYNTAX  INTEGER {
                      disable(0),
                      enable(1)
                   }
                   ACCESS  read-write
                   STATUS  mandatory
                   DESCRIPTION
                   "If this is enabled, the management module will monitor for Hot Air
                    Recirculation by detecting non-uniform air temperature(s) that may
                    be entering the front of the chassis.

                    This could be due to either localized hot or cold air reaching at
                    least one of the node's or chassis temperature sensors and it
                    exceeding the acceptable range. When enabled, this monitor will
                    generate an event and be transmitted to any configured remote
                    alert recipient."

                   ::= { monitorTemp 3 }

     hotAirRecircTempDeltaThresh OBJECT-TYPE
                   SYNTAX  INTEGER
                   ACCESS  read-write
                   STATUS  mandatory
                   DESCRIPTION
                   "This object is used to read or change the temperature delta threshold for
                    Hot Air Recirculation detection. Values are enforced to be in the inclusive
                    range between 5.00C and 9.00C and are specified as hundreths of a degree. For
                    example, a value of 659 would equate to a threshold of 6.59 degrees C."

                   ::= { monitorTemp 5 }

     hotAirRecircStatusTable OBJECT-TYPE
                    SYNTAX  SEQUENCE OF HotAirRecircStatusEntry
                    ACCESS  not-accessible
                    STATUS  mandatory
                    DESCRIPTION
                    "Table of hot air recirculation status information."
                    ::= { monitorTemp 7 }

     hotAirRecircStatusEntry OBJECT-TYPE
                     SYNTAX HotAirRecircStatusEntry
                     ACCESS  not-accessible
                     STATUS  mandatory
                     DESCRIPTION
                     "Hot air recirculation status entry"
                     INDEX { hotAirRecircStatusTopologyPath, hotAirRecircStatusIndex }
                     ::= { hotAirRecircStatusTable 1 }


     HotAirRecircStatusEntry ::= SEQUENCE {
                   hotAirRecircStatusTopologyPath OCTET STRING,
                   hotAirRecircStatusIndex INTEGER,
                   hotAirRecircStatusName OCTET STRING,
                   hotAirRecircStatusSensorLabel OCTET STRING,
                   hotAirRecircStatusSensorReading OCTET STRING,
                   hotAirRecircStatusExceeded INTEGER
                   }

     hotAirRecircStatusTopologyPath  OBJECT-TYPE
                   SYNTAX  OCTET STRING  (SIZE (0..100))
                   ACCESS  read-only
                   STATUS  mandatory
                   DESCRIPTION
                   "The unique identifier for a component in this table. The chassis and each
                    installed component is represented by a hardware topology tree, where
                    each node in the tree represents a component. The path to a particular
                    component consists of one or more <component>,<instance> pairs, where
                    each successive pair is a child of the previous parent pair.

                    As an example, the root of the tree is the chassis and is represented
                    by the pair 'CHASSIS, 1'. This pair indicates the first instance of
                    the chassis. If a blade is inserted in slot 4 of the chassis, its
                    topology path is 'CHASSIS, 1, BLADE, 4'. With this format, the
                    components in the chassis can be determined along with their relative
                    hierarchy to each other.

                    Note that this TP is preceded by a single octet that specifies the TP length.
                    This is required since this table is indexed with two indices and, therefore,
                    the TP length must be explicitly provided.

                    This component firmware table is indexed by this unique topology
                    path and the numeric designations for the components are:

                     CHASSIS,                0x01   Chassis
                     MM,                     0x02   Management Module
                     BLADE,                  0x03   Main system board of a blade
                     POWER,                  0x04   Power Supply, Power Module, etc
                     COOLING,                0x05   Fan, blower, or other cooling device
                     IO_MODULE,              0x06   Has I/O interface, i.e. - switch or bridge
                     MEDIA,                  0x07   Media device
                     PROCESSOR,              0x08   Any processor, processor module, etc
                     STORAGE,                0x09   Any type of storage device
                     EXPANSION,              0x0A   Expansion Card (not covered by more specific type)
                     MEMORY,                 0x0B   Any memory device, module, etc
                     MFRU,                   0x0C   Managed FRU Device
                     PANEL,                  0x0D   Any sort of panel device, such as a front panel
                     BLADE_EXPANSION_MODULE, 0x0E   Expansion option (BEM) such as PEU, BSE, etc
                     CARD_EXPANSION,         0x0F   Expansion card, ie. daughter card
                     CARD_HS_EXPANSION,      0x10   High Speed Expansion card, ie. daughter card
                     INTERPOSER,             0x11   Interposer device
                     CLOCK,                  0x12   Clock card
                     MUX,                    0x13   Mulitplexer card
                     ADDIN,                  0x14   cKVM card & other addin cards
                     STORAGE_MODULE,         0x15   Container of one or more Storage Devices
                     SYS_EXPANSION_CARD,     0x16   Management card
                     BATTERY,                0x17   A single battery
                     BATTERY_MODULE,         0x18   Container of one or more batteries
                     REAR_LED,               0x19   Rear LED card
                     MEMORY_BANK,            0x1A   Memory banks
                     AIR_FILTER,             0x1B   Filter mechanism (bezel)
                     SERIAL_PORT_MODULE,     0x1C   Container of one or more serial ports
                     PARENT,                 0x1D   Reference to parent for multi-parent support
                     PHY_PORT,               0x1E   Physical port
                     IO_EXPANDER,            0x1F   RAID card
                     CABLE,                  0x20   Cable/Interconnect
                     FAN_MUX                 0x29   Fan multiplexer card
                     PCI_EXPRESS,            0x32   PCI express card on (PEN)
                     FLASH_DIMM,             0x33   Used for SPD devices that matches the silkscreen of the DIMM slot
                     RACK,                   0x50   Rack
                     PLATFORM,               0x51   Generic Platform like rack mounted server/appliance
                     DATAPLEX,               0x52   DataPlex
                     OTHER,                  0x53   Other unknown etc.
                     PERIPHERAL_MODULE,      0x54 
                     SYSTEM_BOARD,           0x55   System board
                     PROCESSOR_MODULE,       0x56 
                     BACK_PANEL,             0x57 
                     POWER_SYSTEM_BOARD,     0x58 
                     STORAGE_BACKPLANE,      0x59   Drive back plane
                     PROC_BOARD,             0x5A   Holds 1 or more processors
                     POWER_DI,               0x5B   Power mgt / power distribution board
                     CHASSIS_BACK_PANEL,     0x5C 
                     SUB_CHASSIS,            0x5D 
                     OTHER_CHASSIS_BOARD,    0x5E 
                     DEVICE_MODULE,          0x5F 
                     REMOTE_DEVICE,          0x60   Remote mgt communication device
                     EXTERNAL_ENVIRONMENT,   0x61   Such as external temp sensor for outside box temps
                     PROC_MEMORY_MODULE,     0x62   Processors and memory on same module"
                   ::= { hotAirRecircStatusEntry 2 }

     hotAirRecircStatusIndex OBJECT-TYPE
                  SYNTAX  INTEGER
                  ACCESS  read-only
                  STATUS  mandatory
                  DESCRIPTION
                  "Each component may have one or more sensor associated with it, this index object
                   identifies the particular instance."
                  ::= { hotAirRecircStatusEntry 3 }

     hotAirRecircStatusName OBJECT-TYPE
                  SYNTAX  OCTET STRING
                  ACCESS  read-only
                  STATUS  mandatory
                  DESCRIPTION
                  "The name of the component as a null terminated string"
                  ::= { hotAirRecircStatusEntry 4 }

     hotAirRecircStatusSensorLabel    OBJECT-TYPE
                  SYNTAX  OCTET STRING
                  ACCESS  read-only
                  STATUS  mandatory
                  DESCRIPTION
                  "The text label of the sensor as a null terminated string"
                  ::= { hotAirRecircStatusEntry 5 }

     hotAirRecircStatusSensorReading    OBJECT-TYPE
                  SYNTAX  OCTET STRING
                  ACCESS  read-only
                  STATUS  mandatory
                  DESCRIPTION
                  "Ambient temperature reading for this component in degrees centigrade(C).
                   The string is formatted as 'dd.dd Centigrade'."
                  ::= { hotAirRecircStatusEntry 6 }

     hotAirRecircStatusExceeded    OBJECT-TYPE
                   SYNTAX  INTEGER {
                     no(0),
                     yes(1)
                   }
                   ACCESS  read-only
                   STATUS  mandatory
                   DESCRIPTION
                   "Indicates whether this component has exceeded the threshold
                    of the acceptable temperature being monitored for hot air recirculation."
                   ::= { hotAirRecircStatusEntry 7 }


    -- ********************************************************************************
    -- Chassis Fans 
    -- ********************************************************************************
    chassisFans OBJECT IDENTIFIER ::= { monitors 3 }

    -- ********************************************************************************
    -- Chassis Fans Information Table 
    -- ********************************************************************************
    chassisFansTable OBJECT-TYPE
                    SYNTAX  SEQUENCE OF ChassisFansEntry
                    ACCESS  not-accessible
                    STATUS  mandatory
                    DESCRIPTION
                    "Table of chassis Fan information."
                    ::= { chassisFans 50 }

     chassisFansEntry OBJECT-TYPE
                     SYNTAX ChassisFansEntry
                     ACCESS  not-accessible
                     STATUS  mandatory
                     DESCRIPTION
                     "Chassis Fan information entry"
                     INDEX { chassisFanIndex }
                     ::= { chassisFansTable 1 }


     ChassisFansEntry ::= SEQUENCE {
                   chassisFanIndex INTEGER,
                   chassisFanId INTEGER,
                   chassisFanSpeed OCTET STRING,
                   chassisFanState INTEGER,
                   chassisFanSpeedRPM OCTET STRING, 
                   chassisFanControllerState INTEGER,
                   chassisFanCoolingZone INTEGER
                   }

     chassisFanIndex OBJECT-TYPE
                   SYNTAX  INTEGER (0..128)
                   ACCESS  read-only
                   STATUS  mandatory
                   DESCRIPTION
                   "Chassis Fans table index.  "
                   ::= { chassisFansEntry 1 }

     chassisFanId OBJECT-TYPE
                   SYNTAX  INTEGER {
                   chassisfan1(1),
                   chassisfan2(2),
                   chassisfan3(3),
                   chassisfan4(4),
                   chassisfan5(5),
                   chassisfan6(6),
                   chassisfan7(7),
                   chassisfan8(8),
                   chassisfan9(9),
                   chassisfan10(10)
                   }
                   ACCESS  read-only
                   STATUS  mandatory
                   DESCRIPTION
                   "The numeric chassis fan ID."
                   ::= { chassisFansEntry 2 }

     chassisFanSpeed OBJECT-TYPE
                  SYNTAX  OCTET STRING
                  ACCESS  read-only
                  STATUS  mandatory
                  DESCRIPTION
                  "Chassis fan speed expressed in percent(%) of maximum RPM.
                  An octet string expressed as 'ddd% of maximum' where:
                  d is a decimal digit or blank space for a leading zero.
                  If the chassis fan is determined not to be running or
                  the chassis fan speed cannot be determined, the string will
                  indicate 'Offline'.
                  The string 'Not Readable!' indicates that the given monitor
                  is not supported on this system."
                  ::= { chassisFansEntry 3 }

     chassisFanState  OBJECT-TYPE
                   SYNTAX  INTEGER {
                     unknown(0),
                     good(1),
                     warning(2),
                     bad(3)
                   }
                   ACCESS  read-only
                   STATUS  mandatory
                   DESCRIPTION
                   "The health state for the chassis fan.

                    Note that the other UIs may use slightly different terminology for the 
                    three health state values, as such:

                      WEB - Normal, Attention, Critical
                      CLI - OK, Non-critical, Critical   
                   "
                   ::= { chassisFansEntry 4}

     chassisFanSpeedRPM    OBJECT-TYPE
                  SYNTAX  OCTET STRING
                  ACCESS  read-only
                  STATUS  mandatory
                  DESCRIPTION
                  "Chassis fan speed expressed in RPM.
                  If the chassis fan is determined not to be running or
                  the chassis fan speed cannot be determined, the string will
                  indicate 'Offline'.
                  The string 'Not Readable!' indicates that the given monitor
                  is not supported on this system."
                  ::= { chassisFansEntry 5 }

     chassisFanControllerState    OBJECT-TYPE
                   SYNTAX  INTEGER {
                     operational(0),
                     flashing(1),
                     notPresent(2),
                     communicationError(3),
                     unknown(255)
                   }
                   ACCESS  read-only
                   STATUS  mandatory
                   DESCRIPTION
                   "The controller health state for the chassis fan."
                   ::= { chassisFansEntry 6}

     chassisFanCoolingZone    OBJECT-TYPE
                   SYNTAX  INTEGER {
                     unknown(0),
                     coolingZone1(1),
                     coolingZone2(2),
                     coolingZone3(3),
                     coolingZone4(4)
                   }
                   ACCESS  read-only
                   STATUS  mandatory
                   DESCRIPTION
                   "The cooling zone for the chassis fan."
                   ::= { chassisFansEntry 7}

    -- ********************************************************************************
    -- Chassis Fans Zone Table 
    -- ********************************************************************************
    chassisCoolingZoneTable OBJECT-TYPE
                    SYNTAX  SEQUENCE OF ChassisCoolingZoneEntry
                    ACCESS  not-accessible
                    STATUS  mandatory
                    DESCRIPTION
                    "Table of chassis cooling zone information."
                    ::= { chassisFans 51 }

     chassisCoolingZoneEntry OBJECT-TYPE
                     SYNTAX ChassisCoolingZoneEntry
                     ACCESS  not-accessible
                     STATUS  mandatory
                     DESCRIPTION
                     "Chassis cooling zone information entry"
                     INDEX { chassisCoolingIndex }
                     ::= { chassisCoolingZoneTable 1 }

     ChassisCoolingZoneEntry ::= SEQUENCE {
                   chassisCoolingIndex INTEGER,
                   chassisCoolingZone INTEGER,
                   chassisCoolingZoneStatus INTEGER,
                   chassisCoolingZoneComponent INTEGER
                   }

     chassisCoolingIndex OBJECT-TYPE
                   SYNTAX  INTEGER (0..128)
                   ACCESS  read-only
                   STATUS  mandatory
                   DESCRIPTION
                   "Chassis Cooling Zones table index."
                   ::= { chassisCoolingZoneEntry 1 }

     chassisCoolingZone    OBJECT-TYPE
                   SYNTAX  INTEGER {
                     coolingZone1(1),
                     coolingZone2(2),
                     coolingZone3(3),
                     coolingZone4(4)
                   }
                   ACCESS  read-only
                   STATUS  mandatory
                   DESCRIPTION
                   "The cooling zone for the chassis component."
                   ::= { chassisCoolingZoneEntry 2 }

     chassisCoolingZoneStatus    OBJECT-TYPE
                   SYNTAX  INTEGER {
                     unknown(0),
                     good(1),
                     warning(2),
                     bad(3)
                   }
                   ACCESS  read-only
                   STATUS  mandatory
                   DESCRIPTION
                   "The health state of the chassis cooling zone.
                   Note: This is the health of the cooling zone, not the health
                   status of the component in chassisCoolingZoneComponent.

                    Note that the other UIs may use slightly different terminology for the 
                    three health state values, as such:

                      WEB - Normal, Attention, Critical
                      CLI - OK, Non-critical, Critical   
                   "
                   ::= { chassisCoolingZoneEntry 3 }

     chassisCoolingZoneComponent    OBJECT-TYPE
                   SYNTAX  INTEGER {
                     blade1(1),
                     blade2(2),
                     blade3(3),
                     blade4(4),
                     blade5(5),
                     blade6(6),
                     blade7(7),
                     blade8(8),
                     blade9(9),
                     blade10(10),
                     blade11(11),
                     blade12(12),
                     blade13(13),
                     blade14(14),
                     switchModule1(41),
                     switchModule2(42),
                     switchModule3(43),
                     switchModule4(44),
                     mgmtModule1(61),
                     mgmtModule2(62),
                     fan1(81),
                     fan2(82),
                     fan3(83),
                     fan4(84),
                     fan5(85),
                     fan6(86),
                     fan7(87),
                     fan8(88),
                     fan9(89),
                     fan10(90)
                   }
                   ACCESS  read-only
                   STATUS  mandatory
                   DESCRIPTION
                   "A component within a cooling zone."
                   ::= { chassisCoolingZoneEntry 4 }

    -- ********************************************************************************
    -- Power Module Health State
    -- ********************************************************************************
    powerModuleHealth OBJECT IDENTIFIER ::= { monitors 4 }

      powerModuleHealthTable OBJECT-TYPE
                     SYNTAX  SEQUENCE OF PowerModuleHealthEntry
                     ACCESS  not-accessible
                     STATUS  mandatory
                     DESCRIPTION
                     "Table of power module health information.  Contains
                     the power health information for each power module."
                     ::= { powerModuleHealth 1 }

       powerModuleHealthEntry OBJECT-TYPE
                     SYNTAX PowerModuleHealthEntry
                     ACCESS  not-accessible
                     STATUS  mandatory
                     DESCRIPTION
                     "Power Module health entry"
                     INDEX { powerModuleIndex }
                     ::= { powerModuleHealthTable 1 }

       PowerModuleHealthEntry ::= SEQUENCE {
                   powerModuleIndex INTEGER,
                   powerModuleExists INTEGER,
                   powerModuleState INTEGER,
                   powerModuleDetails OCTET STRING,
                   powerModuleDescription OCTET STRING
                   }

       powerModuleIndex  OBJECT-TYPE
                   SYNTAX  INTEGER
                   ACCESS  read-only
                   STATUS  mandatory
                   DESCRIPTION
                   "Power module index."
                   ::= { powerModuleHealthEntry 1 }

       powerModuleExists OBJECT-TYPE
                   SYNTAX  INTEGER {
                     false(0),
                     true(1)
                   }
                   ACCESS  read-only
                   STATUS  mandatory
                   DESCRIPTION
                   "Indicates whether the power module specified exists or not."
                   ::= { powerModuleHealthEntry 2 }

       powerModuleState OBJECT-TYPE
                   SYNTAX  INTEGER {
                     unknown(0),
                     good(1),
                     warning(2),
                     notAvailable(3),
                     critical(4)
                   }
                   ACCESS  read-only
                   STATUS  mandatory
                   DESCRIPTION
                   "The health state for the power module.

                    Note that the other UIs may use slightly different terminology for the 
                    three health state values, as such:

                      WEB - Normal, Attention, Critical
                      CLI - OK, Non-critical, Critical   
                   "
                   ::= { powerModuleHealthEntry 3}

       powerModuleDetails OBJECT-TYPE
                   SYNTAX  OCTET STRING
                   ACCESS  read-only
                   STATUS  mandatory
                   DESCRIPTION
                   "The details for this power module."
                   ::= { powerModuleHealthEntry 4 }

       powerModuleDescription OBJECT-TYPE
                   SYNTAX  OCTET STRING
                   ACCESS  read-only
                   STATUS  mandatory
                   DESCRIPTION
                   "The description for this power module."
                   ::= { powerModuleHealthEntry 9 }

    -- ********************************************************************************
    -- MM Status
    -- ********************************************************************************
    spStatus OBJECT IDENTIFIER ::= { monitors 5 }

    -- ********************************************************************************
    -- Primary BIST
    -- ********************************************************************************
     mmBistAndChassisStatus OBJECT IDENTIFIER ::= { spStatus 2 }

      bistRtc OBJECT-TYPE
                  SYNTAX  INTEGER {
                    testSucceeded(0),
                    testFailed(1)
                  }
                  ACCESS  read-only
                  STATUS  mandatory
                  DESCRIPTION
                  "MM BIST Real Time Clock test result."
                  ::= { mmBistAndChassisStatus 5 }

      bistLocalI2CBus OBJECT-TYPE
                  SYNTAX  INTEGER {
                    testSucceeded(0),
                    testFailed(1)
                  }
                  ACCESS  read-only
                  STATUS  mandatory
                  DESCRIPTION
                  "MM BIST Local I2C bus test result."
                  ::= { mmBistAndChassisStatus 7 }

      bistPrimaryMainAppFlashImage  OBJECT-TYPE
                  SYNTAX  INTEGER {
                    testSucceeded(0),
                    testFailed(1)
                  }
                  ACCESS  read-only
                  STATUS  mandatory
                  DESCRIPTION
                  "MM BIST Primary Main Application Firmware test result."
                  ::= { mmBistAndChassisStatus 8 }

      bistSecondaryMainAppFlashImage  OBJECT-TYPE
                  SYNTAX  INTEGER {
                    testSucceeded(0),
                    testFailed(1)
                  }
                  ACCESS  read-only
                  STATUS  mandatory
                  DESCRIPTION
                  "MM BIST Secondary Main Application test result."
                  ::= { mmBistAndChassisStatus 9 }

      bistBootRomFlashImage  OBJECT-TYPE
                  SYNTAX  INTEGER {
                    testSucceeded(0),
                    testFailed(1)
                  }
                  ACCESS  read-only
                  STATUS  mandatory
                  DESCRIPTION
                  "MM BIST Boot Firmware test result."
                  ::= { mmBistAndChassisStatus 10 }

      bistEthernetPort1 OBJECT-TYPE
                  SYNTAX  INTEGER {
                    testSucceeded(0),
                    testFailed(1)
                  }
                  ACCESS  read-only
                  STATUS  mandatory
                  DESCRIPTION
                  "MM BIST external eth0 ethernet port test result."
                  ::= { mmBistAndChassisStatus 11 }

      bistExternalI2CDevices OBJECT-TYPE
                  SYNTAX  INTEGER {
                    testSucceeded(0),
                    testFailed(1)
                  }
                  ACCESS  read-only
                  STATUS  mandatory
                  DESCRIPTION
                  "MM BIST external I2C devices test result."
                  ::= { mmBistAndChassisStatus 14 }

      bistInternalEthernetSwitch OBJECT-TYPE
                  SYNTAX  INTEGER {
                    testSucceeded(0),
                    testFailed(1)
                  }
                  ACCESS  read-only
                  STATUS  mandatory
                  DESCRIPTION
                  "MM BIST internal external switch test result."
                  ::= { mmBistAndChassisStatus 19 }

      bistPrimaryKernel OBJECT-TYPE
                  SYNTAX  INTEGER {
                    testSucceeded(0),
                    testFailed(1)
                  }
                  ACCESS  read-only
                  STATUS  mandatory
                  DESCRIPTION
                  "MM BIST primary kernel test result."
                  ::= { mmBistAndChassisStatus 25 }

      bistSecondaryKernel OBJECT-TYPE
                  SYNTAX  INTEGER {
                    testSucceeded(0),
                    testFailed(1)
                  }
                  ACCESS  read-only
                  STATUS  mandatory
                  DESCRIPTION
                  "MM BIST secondary kernel test result."
                  ::= { mmBistAndChassisStatus 26 }

      bistPhysicalNetworkLink OBJECT-TYPE
                  SYNTAX  INTEGER {
                    testSucceeded(0),
                    testFailed(1)
                  }
                  ACCESS  read-only
                  STATUS  mandatory
                  DESCRIPTION
                  "MM BIST Physical Network Link test result."
                  ::= { mmBistAndChassisStatus 29 }

      bistLogicalNetworkLink OBJECT-TYPE
                  SYNTAX  INTEGER {
                    testSucceeded(0),
                    testFailed(1)
                  }
                  ACCESS  read-only
                  STATUS  mandatory
                  DESCRIPTION
                  "MM BIST Logical Network Link test result."
                  ::= { mmBistAndChassisStatus 30 }

      bistBladesInstalled OBJECT-TYPE
                  SYNTAX  OCTET STRING
                  ACCESS  read-only
                  STATUS  mandatory
                  DESCRIPTION
                  "The blades that are installed on the chassis.
                  The blades are listed as a bitmap.  The bitmap is a
                  string containing a list of 1's and 0's that is as long as
                  the number of blades supported.  If a blade is installed in a
                  bay, a 1 is present in the string in the position representing
                  the bay ID as read from left to right.  For example, if blades
                  are installed in bays 1, 5, and 13, and 14 blades are supported,
                  the string would look like '10001000000010'."
                  ::= { mmBistAndChassisStatus 33 }

      bistBladesCommunicating OBJECT-TYPE
                  SYNTAX  OCTET STRING
                  ACCESS  read-only
                  STATUS  mandatory
                  DESCRIPTION
                  "The blades that are communicating on the chassis.
                  The blades are listed as a bitmap.  The bitmap is a
                  string containing a list of 1's and 0's that is as long as
                  the number of blades supported.  If a blade installed in a
                  bay is communicating, a 1 is present in the string in the position
                  representing the bay ID as read from left to right.  For example,
                  if blades are communicating in bays 1, 5, and 13, and 14 blades
                  are supported, the string would look like '10001000000010'."
                  ::= { mmBistAndChassisStatus 49 }

      bistChassisFansInstalled OBJECT-TYPE
                  SYNTAX  OCTET STRING
                  ACCESS  read-only
                  STATUS  mandatory
                  DESCRIPTION
                  "The chassis fans that are installed on the chassis.
                  They are listed as a bitmap.  The bitmap is a
                  string containing a list of 1's and 0's that is as long as
                  the number supported.  If one is installed in a
                  bay, a 1 is present in the string in the position representing
                  the bay ID as read from left to right.  For example, if it
                  is installed in bay 1, and 2 are supported, the string
                  would look like '10'."
                  ::= { mmBistAndChassisStatus 65 }

      bistChassisFansFunctional OBJECT-TYPE
                  SYNTAX  OCTET STRING
                  ACCESS  read-only
                  STATUS  mandatory
                  DESCRIPTION
                  "The chassis fans installed on the chassis that are functional.
                  They are listed as a bitmap.  The bitmap is a
                  string containing a list of 1's and 0's that is as long as
                  the number supported.  If one is installed in a
                  bay, a 1 is present in the string in the position representing
                  the bay ID as read from left to right.  For example, if it
                  is installed in bay 1, and 2 are supported, the string
                  would look like '10'."
                  ::= { mmBistAndChassisStatus 73 }

      bistRearLEDCardInstalled OBJECT-TYPE
                  SYNTAX  INTEGER {
                    no(0),
                    yes(1)
                  }
                  ACCESS  read-only
                  STATUS  mandatory
                  DESCRIPTION
                  "Indicates whether a rear LED card is installed"
                  ::= { mmBistAndChassisStatus 74 }

      bistRearLEDCardCommunicating OBJECT-TYPE
                  SYNTAX  INTEGER {
                    no(0),
                    yes(1)
                  }
                  ACCESS  read-only
                  STATUS  mandatory
                  DESCRIPTION
                  "Indicates whether a rear LED card is communicating"
                  ::= { mmBistAndChassisStatus 75 }

      bistOtherMMInstalled OBJECT-TYPE
                  SYNTAX  INTEGER {
                    no(0),
                    yes(1)
                  }
                  ACCESS  read-only
                  STATUS  mandatory
                  DESCRIPTION
                  "Indicates whether a redundant MM is installed."
                  ::= { mmBistAndChassisStatus 76 }

      bistOtherMMCommunicating OBJECT-TYPE
                  SYNTAX  INTEGER {
                    no(0),
                    yes(1)
                  }
                  ACCESS  read-only
                  STATUS  mandatory
                  DESCRIPTION
                  "Indicates whether a redundant MM is communicating."
                  ::= { mmBistAndChassisStatus 77 }

      bistPowerModulesInstalled OBJECT-TYPE
                  SYNTAX  OCTET STRING
                  ACCESS  read-only
                  STATUS  mandatory
                  DESCRIPTION
                  "The power modules that are installed on the chassis.
                  The power modules are listed as a bitmap.  The bitmap is a
                  string containing a list of 1's and 0's that is as long as
                  the number of power modules supported.  If a power module is
                  installed in a bay, a 1 is present in the string in the position
                  representing the bay ID as read from left to right.  For example,
                  if power modules are installed in bays 1 and 3, and 4 power modules
                  are supported, the string would look like '1010'."
                  ::= { mmBistAndChassisStatus 81 }

      bistPowerModulesFunctional OBJECT-TYPE
                  SYNTAX  OCTET STRING
                  ACCESS  read-only
                  STATUS  mandatory
                  DESCRIPTION
                  "The power modules that are functional on the chassis.
                  The power modules are listed as a bitmap.  The bitmap is a
                  string containing a list of 1's and 0's that is as long as
                  the number of power modules supported.  If a power module is
                  installed and functioning in a bay, a 1 is present in the string
                  in the position representing the bay ID as read from left to right.
                  For example, if power modules are installed and functioning in bays
                  1 and 3, and 4 power modules are supported, the string would look
                  like '1010'."
                  ::= { mmBistAndChassisStatus 89 }

      bistSwitchModulesInstalled OBJECT-TYPE
                  SYNTAX  OCTET STRING
                  ACCESS  read-only
                  STATUS  mandatory
                  DESCRIPTION
                  "The switch modules that are installed on the chassis.
                  The switch modules are listed as a bitmap.  The bitmap is a
                  string containing a list of 1's and 0's that is as long as
                  the number of switch modules supported.  If a switch module is
                  installed in a bay, a 1 is present in the string in the position
                  representing the bay ID as read from left to right.  For example,
                  if switch modules are installed in bays 1 and 3, and 4 switch modules
                  are supported, the string would look like '1011'."
                  ::= { mmBistAndChassisStatus 97 }

      bistSwitchModulesCommunicating OBJECT-TYPE
                  SYNTAX  OCTET STRING
                  ACCESS  read-only
                  STATUS  mandatory
                  DESCRIPTION
                  "The switch modules that are communicating on the chassis.
                  The switch modules are listed as a bitmap.  The bitmap is a
                  string containing a list of 1's and 0's that is as long as
                  the number of switch modules supported.  If a switch module is
                  installed and functioning in a bay, a 1 is present in the string
                  in the position representing the bay ID as read from left to right.
                  For example, if switch modules are installed and functioning in bays
                  1 and 3, and 4 switch modules are supported, the string would look
                  like '1011'."
                  ::= { mmBistAndChassisStatus 113 }

      bistChassisFansMUXAInstalled OBJECT-TYPE
                  SYNTAX  INTEGER {
                    no(0),
                    yes(1)
                  }
                  ACCESS  read-only
                  STATUS  mandatory
                  DESCRIPTION
                  "Indicates whether chassis fan MUX A is installed"
                  ::= { mmBistAndChassisStatus 120 }

      bistChassisFansMUXAFunctional OBJECT-TYPE
                  SYNTAX  INTEGER {
                    no(0),
                    yes(1)
                  }
                  ACCESS  read-only
                  STATUS  mandatory
                  DESCRIPTION
                  "Indicates whether chassis fan MUX A is functional"
                  ::= { mmBistAndChassisStatus 121 }

      bistChassisFansMUXBInstalled OBJECT-TYPE
                  SYNTAX  INTEGER {
                    no(0),
                    yes(1)
                  }
                  ACCESS  read-only
                  STATUS  mandatory
                  DESCRIPTION
                  "Indicates whether chassis fan MUX B is installed"
                  ::= { mmBistAndChassisStatus 122 }

      bistChassisFansMUXBFunctional OBJECT-TYPE
                  SYNTAX  INTEGER {
                    no(0),
                    yes(1)
                  }
                  ACCESS  read-only
                  STATUS  mandatory
                  DESCRIPTION
                  "Indicates whether chassis fan MUX B is functional"
                  ::= { mmBistAndChassisStatus 123 }

      bistLastUpdate OBJECT-TYPE
                  SYNTAX  OCTET STRING
                  ACCESS  read-only
                  STATUS  mandatory
                  DESCRIPTION
                  "It is the time when the primary MM updated the last BIST results."
                  ::= { mmBistAndChassisStatus 200 }

    -- ********************************************************************************
    -- Standby BIST
    -- ********************************************************************************
     rmmBistAndChassisStatus OBJECT IDENTIFIER ::= { spStatus 3 }


      rbistRtc OBJECT-TYPE
                  SYNTAX  INTEGER {
                    testSucceeded(0),
                    testFailed(1)
                  }
                  ACCESS  read-only
                  STATUS  mandatory
                  DESCRIPTION
                  "Standby MM BIST Real Time Clock test result. The time of the last update
                  can be obtained by querying rbistUpdateTime object."
                  ::= { rmmBistAndChassisStatus 5 }

      rbistLocalI2CBus OBJECT-TYPE
                  SYNTAX  INTEGER {
                    testSucceeded(0),
                    testFailed(1)
                  }
                  ACCESS  read-only
                  STATUS  mandatory
                  DESCRIPTION
                  "Standby MM BIST Local I2C bus test result. The time of the last update
                  can be obtained by querying rbistUpdateTime object."
                  ::= { rmmBistAndChassisStatus 7 }

      rbistEthernetPort1 OBJECT-TYPE
                  SYNTAX  INTEGER {
                    testSucceeded(0),
                    testFailed(1)
                  }
                  ACCESS  read-only
                  STATUS  mandatory
                  DESCRIPTION
                  "Standby MM BIST external ethernet port test result. The time of the last update
                  can be obtained by querying rbistUpdateTime object."
                  ::= { rmmBistAndChassisStatus 11 }

      rbistExternalI2CDevices OBJECT-TYPE
                  SYNTAX  INTEGER {
                    testSucceeded(0),
                    testFailed(1)
                  }
                  ACCESS  read-only
                  STATUS  mandatory
                  DESCRIPTION
                  "Standby MM BIST external I2C devices test result collected
                  when the standby MM was primary. The time of the last update
                  can be obtained by querying rbistUpdateTimePrimary object."
                  ::= { rmmBistAndChassisStatus 14 }

      rbistInternalEthernetSwitch OBJECT-TYPE
                  SYNTAX  INTEGER {
                    testSucceeded(0),
                    testFailed(1)
                  }
                  ACCESS  read-only
                  STATUS  mandatory
                  DESCRIPTION
                  "Standby MM BIST internal external switch test result.
                  The time of the last update can be obtained by querying rbistUpdateTime object."
                  ::= { rmmBistAndChassisStatus 19 }


      rbistPhysicalNetworkLink OBJECT-TYPE
                  SYNTAX  INTEGER {
                    testSucceeded(0),
                    testFailed(1)
                  }
                  ACCESS  read-only
                  STATUS  mandatory
                  DESCRIPTION
                  "Standby MM BIST Physical Network Link test result collected
                  when the standby MM was primary. The time of the last update
                  can be obtained by querying rbistUpdateTimePrimary object."
                  ::= { rmmBistAndChassisStatus 29 }

      rbistLogicalNetworkLink OBJECT-TYPE
                  SYNTAX  INTEGER {
                    testSucceeded(0),
                    testFailed(1)
                  }
                  ACCESS  read-only
                  STATUS  mandatory
                  DESCRIPTION
                  "Standby MM BIST Logical Network Link test result collected
                  when the standby MM was primary. The time of the last update
                  can be obtained by querying rbistUpdateTimePrimary object."
                  ::= { rmmBistAndChassisStatus 30 }

      rbistBladesInstalled OBJECT-TYPE
                  SYNTAX  OCTET STRING
                  ACCESS  read-only
                  STATUS  mandatory
                  DESCRIPTION
                  "The blades that were installed on the chassis when the
                  standby MM was once primary. The time of the last update
                  can be obtained by querying rbistUpdateTimePrimary object.
                  The blades are listed as a bitmap.  The bitmap is a
                  string containing a list of 1's and 0's that is as long as
                  the number of blades supported.  If a blade is installed in a
                  bay, a 1 is present in the string in the position representing
                  the bay ID as read from left to right.  For example, if blades
                  are installed in bays 1, 5, and 13, and 14 blades are supported,
                  the string would look like '10001000000010'. "
                  ::= { rmmBistAndChassisStatus 33 }

      rbistBladesCommunicating OBJECT-TYPE
                  SYNTAX  OCTET STRING
                  ACCESS  read-only
                  STATUS  mandatory
                  DESCRIPTION
                  "The blades that were communicating on the chassis when the
                  standby MM was once primary. The time of the last update
                  can be obtained by querying rbistUpdateTimePrimary object.
                  The blades are listed as a bitmap.  The bitmap is a
                  string containing a list of 1's and 0's that is as long as
                  the number of blades supported.  If a blade installed in a
                  bay is communicating, a 1 is present in the string in the position
                  representing the bay ID as read from left to right.  For example,
                  if blades are communicating in bays 1, 5, and 13, and 14 blades
                  are supported, the string would look like '10001000000010'."
                  ::= { rmmBistAndChassisStatus 49 }

      rbistChassisFansInstalled OBJECT-TYPE
                  SYNTAX  OCTET STRING
                  ACCESS  read-only
                  STATUS  mandatory
                  DESCRIPTION
                  "The chassis fans that were installed on the chassis when the
                  standby MM was once primary. The time of the last update
                  can be obtained by querying rbistUpdateTimePrimary object.

                  They are listed as a bitmap.  The bitmap is a
                  string containing a list of 1's and 0's that is as long as
                  the number of chassis fans supported.  If it is installed in a
                  bay, a 1 is present in the string in the position representing
                  the bay ID as read from left to right.  For example, if it
                  is installed in bay 1, and 2 are supported, the string
                  would look like '10'."
                  ::= { rmmBistAndChassisStatus 65 }

      rbistChassisFansFunctional OBJECT-TYPE
                  SYNTAX  OCTET STRING
                  ACCESS  read-only
                  STATUS  mandatory
                  DESCRIPTION
                  "The chassis fans installed on the chassis that were functional when the
                  standby MM was once primary. The time of the last update
                  can be obtained by querying rbistUpdateTimePrimary object.

                  They are listed as a bitmap.  The bitmap is a
                  string containing a list of 1's and 0's that is as long as
                  the number supported.  If it is installed and
                  functional in a bay, a 1 is present in the string in the position
                  representing the bay ID as read from left to right.  For example,
                  if one is installed and functional only in bay 1, and 2 
                  are supported, the string would look like '10'."
                  ::= { rmmBistAndChassisStatus 73 }

       rbistRearLEDCardInstalled OBJECT-TYPE
                  SYNTAX  INTEGER {
                    no(0),
                    yes(1)
                  }
                  ACCESS  read-only
                  STATUS  mandatory
                  DESCRIPTION
                  "Indicates whether a rear LED card is installed"
                  ::= { rmmBistAndChassisStatus 74 }

      rbistRearLEDCardCommunicating OBJECT-TYPE
                  SYNTAX  INTEGER {
                    no(0),
                    yes(1)
                  }
                  ACCESS  read-only
                  STATUS  mandatory
                  DESCRIPTION
                  "Indicates whether a rear LED card is communicating"
                  ::= { rmmBistAndChassisStatus 75 }

       rbistOtherMMInstalled OBJECT-TYPE
                  SYNTAX  INTEGER {
                    no(0),
                    yes(1)
                  }
                  ACCESS  read-only
                  STATUS  mandatory
                  DESCRIPTION
                  "Indicates whether a standby MM was installed when the
                  standby MM was once primary.The time of the last update
                  can be obtained by querying rbistUpdateTimePrimary object."
                  ::= { rmmBistAndChassisStatus 76 }

      rbistOtherMMCommunicating OBJECT-TYPE
                  SYNTAX  INTEGER {
                    no(0),
                    yes(1)
                  }
                  ACCESS  read-only
                  STATUS  mandatory
                  DESCRIPTION
                  "Indicates whether a standby MM was communicating when the
                  standby MM was once primary. The time of the last update can be
                  gotten from the object 'rbistUpdateTimePrimary'."
                  ::= { rmmBistAndChassisStatus 77 }

      rbistPowerModulesInstalled OBJECT-TYPE
                  SYNTAX  OCTET STRING
                  ACCESS  read-only
                  STATUS  mandatory
                  DESCRIPTION
                  "The power modules that were installed on the chassis when the
                  standby MM was once primary. The time of the last update
                  can be obtained by querying rbistUpdateTimePrimary object.
                  The power modules are listed as a bitmap.  The bitmap is a
                  string containing a list of 1's and 0's that is as long as
                  the number of power modules supported.  If a power module was
                  installed in a bay, a 1 is present in the string in the position
                  representing the bay ID as read from left to right.  For example,
                  if power modules were installed in bays 1 and 3, and 4 power modules
                  were supported, the string would look like '1010'."
                  ::= { rmmBistAndChassisStatus 81 }

      rbistPowerModulesFunctional OBJECT-TYPE
                  SYNTAX  OCTET STRING
                  ACCESS  read-only
                  STATUS  mandatory
                  DESCRIPTION
                  "The power modules that were functional on the chassis when the
                  standby MM was once primary. The time of the last update
                  can be obtained by querying rbistUpdateTimePrimary object.
                  The power modules are listed as a bitmap.  The bitmap is a
                  string containing a list of 1's and 0's that is as long as
                  the number of power modules supported.  If a power module was
                  installed and functioning in a bay, a 1 is present in the string
                  in the position representing the bay ID as read from left to right.
                  For example, if power modules were installed and functioning in bays
                  1 and 3, and 4 power modules were supported, the string would look
                  like '1010'."
                  ::= { rmmBistAndChassisStatus 89 }

      rbistSwitchModulesInstalled OBJECT-TYPE
                  SYNTAX  OCTET STRING
                  ACCESS  read-only
                  STATUS  mandatory
                  DESCRIPTION
                  "The switch modules that were installed on the chassis when the
                  standby MM was once primary. The time of the last update
                  can be obtained by querying rbistUpdateTimePrimary object.
                  The switch modules are listed as a bitmap.  The bitmap is a
                  string containing a list of 1's and 0's that is as long as
                  the number of switch modules supported.  If a switch module was
                  installed in a bay, a 1 is present in the string in the position
                  representing the bay ID as read from left to right.  For example,
                  if switch modules were installed in bays 1 and 3, and 4 switch modules
                  were supported, the string would look like '1011'."
                  ::= { rmmBistAndChassisStatus 97 }

      rbistSwitchModulesCommunicating OBJECT-TYPE
                  SYNTAX  OCTET STRING
                  ACCESS  read-only
                  STATUS  mandatory
                  DESCRIPTION
                  "The switch modules that are communicating on the chassis when the
                  standby MM was once primary. The time of the last update
                  can be obtained by querying rbistUpdateTimePrimary object.
                  The switch modules are listed as a bitmap.  The bitmap is a
                  string containing a list of 1's and 0's that is as long as
                  the number of switch modules supported.  If a switch module was
                  installed and functioning in a bay, a 1 is present in the string
                  in the position representing the bay ID as read from left to right.
                  For example, if switch modules were installed and functioning in bays
                  1 and 3, and 4 switch modules were supported, the string would look
                  like '1011'."
                  ::= { rmmBistAndChassisStatus 113 }

      rbistChassisFansMUXAInstalled OBJECT-TYPE
                  SYNTAX  INTEGER {
                    no(0),
                    yes(1)
                  }
                  ACCESS  read-only
                  STATUS  mandatory
                  DESCRIPTION
                  "Indicates whether chassis fan MUX A is installed"
                  ::= { rmmBistAndChassisStatus 120 }

      rbistChassisFansMUXAFunctional OBJECT-TYPE
                  SYNTAX  INTEGER {
                    no(0),
                    yes(1)
                  }
                  ACCESS  read-only
                  STATUS  mandatory
                  DESCRIPTION
                  "Indicates whether chassis fan MUX A is functional"
                  ::= { rmmBistAndChassisStatus 121 }

      rbistChassisFansMUXBInstalled OBJECT-TYPE
                  SYNTAX  INTEGER {
                    no(0),
                    yes(1)
                  }
                  ACCESS  read-only
                  STATUS  mandatory
                  DESCRIPTION
                  "Indicates whether chassis fan MUX B is installed"
                  ::= { rmmBistAndChassisStatus 122 }

      rbistChassisFansMUXBFunctional OBJECT-TYPE
                  SYNTAX  INTEGER {
                    no(0),
                    yes(1)
                  }
                  ACCESS  read-only
                  STATUS  mandatory
                  DESCRIPTION
                  "Indicates whether chassis fan MUX B is functional"
                  ::= { rmmBistAndChassisStatus 123 }

      rbistUpdateTime OBJECT-TYPE
                  SYNTAX  OCTET STRING
                  ACCESS  read-only
                  STATUS  mandatory
                  DESCRIPTION
                  "It is the time when the standby MM updated the last BIST results."
                  ::= { rmmBistAndChassisStatus 200 }

      rbistLastUpdatePrimary OBJECT-TYPE
                  SYNTAX  OCTET STRING
                  ACCESS  read-only
                  STATUS  mandatory
                  DESCRIPTION
                  "It is the time when the standby MM updated the last BIST results
                   when it was still primary."
                  ::= { rmmBistAndChassisStatus 201 }

    -- ********************************************************************************
    -- Power Module Fan Pack Health State
    -- ********************************************************************************
    fanPack OBJECT IDENTIFIER ::= { monitors 6 }

      fanPackTable OBJECT-TYPE
                  SYNTAX  SEQUENCE OF FanPackEntry
                  ACCESS  not-accessible
                  STATUS  mandatory
                  DESCRIPTION
                  "Table of fan pack information.  Contains
                  the information for each fan pack.

                  NOTE: Fan packs are also referred to as Power Module Cooling Devices."
                  ::= { fanPack 1 }

       fanPackEntry OBJECT-TYPE
                  SYNTAX FanPackEntry
                  ACCESS  not-accessible
                  STATUS  mandatory
                  DESCRIPTION
                  "Fan Pack entry"
                  INDEX { fanPackIndex }
                  ::= { fanPackTable 1 }

       FanPackEntry ::= SEQUENCE {
                  fanPackIndex INTEGER,
                  fanPackExists INTEGER,
                  fanPackState INTEGER,
                  fanPackFanCount INTEGER,
                  fanPackAverageSpeed OCTET STRING,
                  fanPackAverageSpeedRPM OCTET STRING,
                  fanPackControllerState INTEGER
                  }

       fanPackIndex  OBJECT-TYPE
                  SYNTAX  INTEGER
                  ACCESS  read-only
                  STATUS  mandatory
                  DESCRIPTION
                  "Fan Pack sequence index."
                  ::= { fanPackEntry 1 }

       fanPackExists OBJECT-TYPE
                  SYNTAX  INTEGER {
                    false(0),
                    true(1)
                  }
                  ACCESS  read-only
                  STATUS  mandatory
                  DESCRIPTION
                  "Indicates whether the fan pack specified exists or not."
                  ::= { fanPackEntry 2 }

       fanPackState OBJECT-TYPE
                  SYNTAX  INTEGER {
                    unknown(0),
                    good(1),
                    warning(2),
                    bad(3)
                  }
                  ACCESS  read-only
                  STATUS  mandatory
                  DESCRIPTION
                  "The health state for the fan pack.

                    Note that the other UIs may use slightly different terminology for the 
                    three health state values, as such:

                      WEB - Normal, Attention, Critical
                      CLI - OK, Non-critical, Critical   
                  "
                  ::= { fanPackEntry 3}

       fanPackFanCount OBJECT-TYPE
                  SYNTAX  INTEGER {
                    unknown(255)
                  }
                  ACCESS  read-only
                  STATUS  mandatory
                  DESCRIPTION
                  "The number of fans in the fan pack."
                  ::= { fanPackEntry 4 }

       fanPackAverageSpeed    OBJECT-TYPE
                  SYNTAX  OCTET STRING
                  ACCESS  read-only
                  STATUS  mandatory
                  DESCRIPTION
                  "The average speed of all fans in the fan pack expressed in percent(%)
                  of maximum RPM. If the fan pack is determined not to be running or
                  the fan pack speed cannot be determined, the string will
                  indicate 'Offline'.  The string 'Not Readable!' indicates that the
                  given monitor is not supported on this system."
                  ::= { fanPackEntry 5 }

       fanPackAverageSpeedRPM    OBJECT-TYPE
                  SYNTAX  OCTET STRING
                  ACCESS  read-only
                  STATUS  mandatory
                  DESCRIPTION
                  "The average speed of all fans in the fan pack expressed in RPM.
                  If the fan pack is determined not to be running or the fan pack speed
                  cannot be determined, the string will indicate 'Offline'. The string
                  'Not Readable!' indicates that the given monitor is not supported on
                  this system."
                  ::= { fanPackEntry 6 }

       fanPackControllerState    OBJECT-TYPE
                  SYNTAX  INTEGER {
                     operational(0),
                     flashing(1),
                     notPresent(2),
                     communicationError(3),
                     unknown(255)
                  }
                  ACCESS  read-only
                  STATUS  mandatory
                  DESCRIPTION
                  "The health state for the controller for the fan pack."
                  ::= { fanPackEntry 7}

    -- ********************************************************************************
    -- System Health
    -- ********************************************************************************
    systemHealth OBJECT IDENTIFIER ::= { monitors 7 }

     -- ********************************************************************************
     -- System Health Status
     -- ********************************************************************************
     systemHealthStat  OBJECT-TYPE
                  SYNTAX  INTEGER {
                                    critical(0),
                                    nonCritical(2),
                                    systemLevel(4),
                                    normal(255)
                                  }
                  ACCESS  read-only
                  STATUS  mandatory
                  DESCRIPTION
                  "Indicates status of system health for the
                  system in which the MM resides.
                  Value of 'critical' indicates a severe error has occurred
                  and the system may not be functioning. A value of
                  'nonCritical' indicates that a error has occurred but
                  the system is currently functioning properly.  A value of
                  'systemLevel' indicates that a condition has occurred
                  that may change the state of the system in the future but currently
                  the system is working properly. A value of
                  'normal' indicates that the system is operating normally.

                  NOTE: The object is not available on a telco chassis. See the 
                        telcoManagement branch of the MIB."
                  ::= { systemHealth 1 }

     -- ********************************************************************************
     -- System Health Summary
     -- ********************************************************************************
     systemHealthSummaryTable OBJECT-TYPE
                   SYNTAX  SEQUENCE OF SystemHealthSummaryEntry
                   ACCESS  not-accessible
                   STATUS  mandatory
                   DESCRIPTION
                   "Table of System Health summary. Contains more detailed
                   information about the reasons for the overall system
                   health status.

                   NOTE: The table is not available on a telco chassis. See the 
                         telcoManagement branch of the MIB."
                   ::= { systemHealth 2 }

     systemHealthSummaryEntry OBJECT-TYPE
                   SYNTAX SystemHealthSummaryEntry
                   ACCESS  not-accessible
                   STATUS  mandatory
                   DESCRIPTION
                   "System Health Summary entry"
                   INDEX { systemHealthSummaryIndex }
                   ::= { systemHealthSummaryTable 1 }


     SystemHealthSummaryEntry ::= SEQUENCE {
                 systemHealthSummaryIndex INTEGER,
                 systemHealthSummarySeverity OCTET STRING,
                 systemHealthSummaryDescription OCTET STRING,
                 systemHealthSummaryDateTime OCTET STRING,
                 systemHealthSummaryAuxData OCTET STRING,
                 systemHealthSummaryEventID OCTET STRING,
                 systemHealthSummaryCommonEventID OCTET STRING
                 }

     systemHealthSummaryIndex  OBJECT-TYPE
                 SYNTAX  INTEGER
                 ACCESS  read-only
                 STATUS  mandatory
                 DESCRIPTION
                 "System health summary index."
                 ::= { systemHealthSummaryEntry 1 }

     systemHealthSummarySeverity  OBJECT-TYPE
                 SYNTAX  OCTET STRING
                 ACCESS  read-only
                 STATUS  mandatory
                 DESCRIPTION
                 "System health summary severity."
                 ::= { systemHealthSummaryEntry 2 }

     systemHealthSummaryDescription  OBJECT-TYPE
                 SYNTAX  OCTET STRING
                 ACCESS  read-only
                 STATUS  mandatory
                 DESCRIPTION
                 "System health summary description."
                 ::= { systemHealthSummaryEntry 3 }

     systemHealthSummaryDateTime  OBJECT-TYPE
                 SYNTAX  OCTET STRING
                 ACCESS  read-only
                 STATUS  mandatory
                 DESCRIPTION
                 "System health summary date time."
                 ::= { systemHealthSummaryEntry 4 }

     systemHealthSummaryAuxData  OBJECT-TYPE
                 SYNTAX  OCTET STRING
                 ACCESS  read-only
                 STATUS  mandatory
                 DESCRIPTION
                 "System health summary auxilliary event data.  If auxilliary
                  event data is available, it is device-specific event data
                  provided to the CMM by the device."
                 ::= { systemHealthSummaryEntry 11 }

     systemHealthSummaryEventID  OBJECT-TYPE
                 SYNTAX  OCTET STRING
                 ACCESS  read-only
                 STATUS  mandatory
                 DESCRIPTION
                 "System health summary event ID."
                 ::= { systemHealthSummaryEntry 12 }

     systemHealthSummaryCommonEventID  OBJECT-TYPE
                 SYNTAX  OCTET STRING
                 ACCESS  read-only
                 STATUS  mandatory
                 DESCRIPTION
                 "System health summary Common Event ID."
                 ::= { systemHealthSummaryEntry 13 }

    -- ********************************************************************************
    -- LEDs
    -- ********************************************************************************
    leds OBJECT IDENTIFIER ::= { monitors 8 }

     -- ********************************************************************************
     -- Front Panel LEDs
     -- ********************************************************************************
     frontPanelLEDs OBJECT IDENTIFIER ::= { leds 1 }

      faultLED OBJECT-TYPE
                   SYNTAX INTEGER {
                     off(0),
                     on(1)
                   }
                   ACCESS  read-only
                   STATUS  mandatory
                   DESCRIPTION
                   "Indicates whether the front panel system error LED is on or off.

                   NOTE: The object is not available on a telco chassis. See the 
                         telcoManagement branch of the MIB."
                   ::= { frontPanelLEDs 1 }

      checkLogLED OBJECT-TYPE
                   SYNTAX INTEGER {
                     off(0),
                     on(1)
                   }
                   ACCESS  read-write
                   STATUS  mandatory
                   DESCRIPTION
                   "Indicates whether the front panel system information LED
                   is on or off.  For Write access, the LED can be turned off
                   only.

                   NOTE: The object is not available on a telco chassis. See the 
                         telcoManagement branch of the MIB."
                   ::= { frontPanelLEDs 2 }

      identifyLED OBJECT-TYPE
                   SYNTAX INTEGER {
                     off(0),
                     on(1),
                     blinking(2),
                     notAvailable(3)
                   }
                   ACCESS  read-write
                   STATUS  mandatory
                   DESCRIPTION
                   "Indicates whether the front panel identity LED is on or off."
                   ::= { frontPanelLEDs 4 }

     -- ********************************************************************************
     -- Blade LEDs
     -- ********************************************************************************
     bladeLEDs OBJECT IDENTIFIER ::= { leds 2 }

     -- ********************************************************************************
     -- Blade Main LEDs
     -- ********************************************************************************
      bladeLEDsTable OBJECT-TYPE
                    SYNTAX  SEQUENCE OF BladeLEDsEntry
                    ACCESS  not-accessible
                    STATUS  mandatory
                    DESCRIPTION
                    "Table of blade status information.
                    
                     NOTE: Querying objects in this table may take significantly longer
                     than normal, so it is recommended that the query timeout be set to 
                     a large value. On a fully populated chassis, the timeout should be set
                     to 120 seconds or more."
                    ::= { bladeLEDs 1 }

       bladeLEDsEntry OBJECT-TYPE
                     SYNTAX BladeLEDsEntry
                     ACCESS  not-accessible
                     STATUS  mandatory
                     DESCRIPTION
                     "Blade system status entry"
                     INDEX { ledBladeIndex }
                     ::= { bladeLEDsTable 1 }

       BladeLEDsEntry ::= SEQUENCE {
                   ledBladeIndex INTEGER,
                   ledBladeId INTEGER,
                   ledBladeExists INTEGER,
                   ledBladePowerState INTEGER,
                   ledBladeHealthState INTEGER,
                   ledBladeName OCTET STRING,
                   ledBladeFault INTEGER,
                   ledBladeCheckLog INTEGER,
                   ledBladeIdentify INTEGER
                   }

       ledBladeIndex OBJECT-TYPE
                   SYNTAX  INTEGER
                   ACCESS  read-only
                   STATUS  mandatory
                   DESCRIPTION
                   "Blade LED table index."
                   ::= { bladeLEDsEntry 1 }

       ledBladeId OBJECT-TYPE
                   SYNTAX  INTEGER {
                       blade1(1),
                       blade2(2),
                       blade3(3),
                       blade4(4),
                       blade5(5),
                       blade6(6),
                       blade7(7),
                       blade8(8),
                       blade9(9),
                       blade10(10),
                       blade11(11),
                       blade12(12),
                       blade13(13),
                       blade14(14)
                   }
                   ACCESS  read-only
                   STATUS  mandatory
                   DESCRIPTION
                   "The numeric blade ID."
                   ::= { bladeLEDsEntry 2 }

       ledBladeExists OBJECT-TYPE
                   SYNTAX  INTEGER {
                     false(0),
                     true(1)
                   }
                   ACCESS  read-only
                   STATUS  mandatory
                   DESCRIPTION
                   "Indicates whether the blade specified exists or not."
                   ::= { bladeLEDsEntry 3 }

       ledBladePowerState  OBJECT-TYPE
                   SYNTAX  INTEGER {
                     off(0),
                     on(1),
                     standby(3),
                     hibernate(4),
                     unknown(255)
                   }
                   ACCESS  read-only
                   STATUS  mandatory
                   DESCRIPTION
                   "Indicates the power state of the blade specified."
                   ::= { bladeLEDsEntry 4 }

       ledBladeHealthState  OBJECT-TYPE
                   SYNTAX  INTEGER {
                     unknown(0),
                     good(1),
                     warning(2),
                     critical(3),
                     kernelMode(4),
                     discovering(5),
                     commError(6),
                     noPower(7),
                     flashing(8),
                     initFailure(9),
                     insufficientPower(10),
                     powerDenied(11),
                     maintMode(12),
                     firehoseDump(13)
                   }
                   ACCESS  read-only
                   STATUS  mandatory
                   DESCRIPTION
                   "The system health state for the blade.

                    Unknown: Blade is in an undefined state.
                    Good: Blade is operating normally.
                    Warning: One or more outstanding warnings exist for this blade.
                    Critical: One or more outstanding critical events for this blade.
                    Kernel Mode: Blade is in kernel mode.
                    Discovering: The MM is currently in the process of discovering this blade.
                    Communications Error: The MM failed to communicate with this blade.
                    No Power: No power to the blade's domain.
                    Flashing: Flashing in progress.
                    Initialization Failure: Blade failed to initialized.
                    Insufficient Power: Not enough power is left in the blade's domain to power the blade.
                    Power Denied: Power was denied to the blade."
                   ::= { bladeLEDsEntry 5 }

       ledBladeName OBJECT-TYPE
                   SYNTAX  OCTET STRING
                   ACCESS  read-only
                   STATUS  mandatory
                   DESCRIPTION
                   "The name of the blade as a null terminated string."
                   ::= { bladeLEDsEntry 6 }

       ledBladeFault  OBJECT-TYPE
                   SYNTAX  INTEGER {
                     off(0),
                     on(1)
                   }
                   ACCESS  read-only
                   STATUS  mandatory
                   DESCRIPTION
                   "Indicates whether the blade fault LED is on or off."
                   ::= { bladeLEDsEntry 7 }

       ledBladeCheckLog  OBJECT-TYPE
                   SYNTAX  INTEGER {
                     off(0),
                     on(1)
                   }
                   ACCESS  read-write
                   STATUS  mandatory
                   DESCRIPTION
                   "Indicates whether the blade check log information LED is on or off.
                   For Write access, the LED can be turned off only."
                   ::= { bladeLEDsEntry 8 }

       ledBladeIdentify OBJECT-TYPE
                   SYNTAX  INTEGER {
                     off(0),
                     on(1),
                     blinking(2)
                   }
                   ACCESS  read-write
                   STATUS  mandatory
                   DESCRIPTION
                   "Indicates whether the blade identify LED is on, off, or blinking."
                   ::= { bladeLEDsEntry 11 }


     -- ********************************************************************************
     -- Blade Detailed LEDs
     -- ********************************************************************************
      bladeLEDsDetailsTable OBJECT-TYPE
                    SYNTAX  SEQUENCE OF BladeLEDsDetailsEntry
                    ACCESS  not-accessible
                    STATUS  mandatory
                    DESCRIPTION
                    "Table of blade LEDs detailed information.
                    
                     NOTE: Querying objects in this table may take significantly longer
                     than normal, so it is recommended that the query timeout be set to 
                     a large value. On a fully populated chassis, the timeout should be set
                     to 120 seconds or more."
                    ::= { bladeLEDs 2 }

       bladeLEDsDetailsEntry OBJECT-TYPE
                     SYNTAX  BladeLEDsDetailsEntry
                     ACCESS  not-accessible
                     STATUS  mandatory
                     DESCRIPTION
                     "Blade LEDs Details entry"
                     INDEX { ledIndex }
                     ::= { bladeLEDsDetailsTable 1 }

       BladeLEDsDetailsEntry ::= SEQUENCE {
                   ledIndex INTEGER,
                   ledBladeBayNumber OCTET STRING,
                   ledBladeComponentType OCTET STRING,
                   ledBladeLabel OCTET STRING,
                   ledBladeState INTEGER,
                   ledBladeLocation OCTET STRING
                   }

       ledIndex  OBJECT-TYPE
                  SYNTAX  INTEGER
                  ACCESS  read-only
                  STATUS  mandatory
                  DESCRIPTION
                  "The LED index number."
                  ::= { bladeLEDsDetailsEntry 1 }

       ledBladeBayNumber  OBJECT-TYPE
                  SYNTAX  OCTET STRING
                  ACCESS  read-only
                  STATUS  mandatory
                  DESCRIPTION
                  "The bay number of the main server blade that the LED is grouped into."
                  ::= { bladeLEDsDetailsEntry 2 }

       ledBladeComponentType OBJECT-TYPE
                  SYNTAX  OCTET STRING
                  ACCESS  read-only
                  STATUS  mandatory
                  DESCRIPTION
                  "Type of the component/subcomponent grouping for this LED."
                  ::= { bladeLEDsDetailsEntry 3 }

       ledBladeLabel OBJECT-TYPE
                  SYNTAX  OCTET STRING
                  ACCESS  read-only
                  STATUS  mandatory
                  DESCRIPTION
                  "Text label for a LED."
                  ::= { bladeLEDsDetailsEntry 4 }

       ledBladeState OBJECT-TYPE
                  SYNTAX  INTEGER {
                     off(0),
                     on(1),
                     blinking(2)


                   }
                  ACCESS  read-only
                  STATUS  mandatory
                  DESCRIPTION
                  "Text description which denotes color or on/off/blink state for a LED."
                  ::= { bladeLEDsDetailsEntry 5 }

       ledBladeLocation OBJECT-TYPE
                  SYNTAX  OCTET STRING
                  ACCESS  read-only
                  STATUS  mandatory
                  DESCRIPTION
                  "Location of this LED."
                  ::= { bladeLEDsDetailsEntry 6 }

     -- ********************************************************************************
     -- Switch Module LEDs
     -- ********************************************************************************
     smLEDs OBJECT IDENTIFIER ::= { leds 4 }

     smLEDsTable   OBJECT-TYPE
                       SYNTAX  SEQUENCE OF SMLEDsEntry
                       ACCESS  not-accessible
                       STATUS  mandatory
                       DESCRIPTION
                       "Table of switch module LEDs information."
                       ::= { smLEDs 2 }

       smLEDsEntry   OBJECT-TYPE
                        SYNTAX SMLEDsEntry
                        ACCESS  not-accessible
                        STATUS  mandatory
                        DESCRIPTION
                        "Switch module LEDs information entry"
                        INDEX { ledSMSlot, ledSMIndex }
                        ::= { smLEDsTable 1 }

       SMLEDsEntry ::= SEQUENCE {
                      ledSMIndex      INTEGER,
                      ledSMSlot       INTEGER,
                      ledSMLabel      OCTET STRING,
                      ledSMState      INTEGER,
                      ledSMLocation   OCTET STRING
                      }

       ledSMIndex  OBJECT-TYPE
                      SYNTAX  INTEGER
                      ACCESS  read-only
                      STATUS  mandatory
                      DESCRIPTION
                      "Switch module LEDs table index."
                      ::= { smLEDsEntry 1 }

       ledSMSlot   OBJECT-TYPE
                      SYNTAX  INTEGER (0..128)
                      ACCESS  read-only
                      STATUS  mandatory
                      DESCRIPTION
                      "The bay number of the switch."
                      ::= { smLEDsEntry 2 }

       ledSMLabel   OBJECT-TYPE
                       SYNTAX  OCTET STRING (SIZE(256))
                       ACCESS  read-only
                       STATUS  mandatory
                       DESCRIPTION
                       "The name associated with the LED."
                       ::= { smLEDsEntry 3 }

       ledSMState  OBJECT-TYPE
                      SYNTAX  INTEGER {
                        off(0),
                        on(1),
                        blinking(2)
                        }
                      ACCESS  read-write
                      STATUS  mandatory
                      DESCRIPTION
                      "NOTE:  This table entry is read-write ONLY when Label = 'Enclosure Identity'.
                      All other Label values have read-only access."
                      ::= { smLEDsEntry 4 }

       ledSMLocation   OBJECT-TYPE
                          SYNTAX  OCTET STRING (SIZE(256))
                          ACCESS  read-only
                          STATUS  mandatory
                          DESCRIPTION
                          "The physical location where the LED can be found on the Switch."
                          ::= { smLEDsEntry 5 }

     -- ********************************************************************************
     -- Chassis Fan LEDs
     -- ********************************************************************************
     chassisFanLEDs OBJECT IDENTIFIER ::= { leds 5 }

      chassisFanLEDsTable OBJECT-TYPE
                    SYNTAX  SEQUENCE OF ChassisFanLEDsEntry
                    ACCESS  not-accessible
                    STATUS  mandatory
                    DESCRIPTION
                    "Table of chassis fan LEDs information."
                    ::= { chassisFanLEDs 1 }

       chassisFanLEDsEntry OBJECT-TYPE
                     SYNTAX ChassisFanLEDsEntry
                     ACCESS  not-accessible
                     STATUS  mandatory
                     DESCRIPTION
                     "Chassis fan LEDs information entry"
                     INDEX { ledChassisFanIndex }
                     ::= { chassisFanLEDsTable 1 }

       ChassisFanLEDsEntry ::= SEQUENCE {
                   ledChassisFanIndex INTEGER,
                   ledChassisFanId INTEGER,
                   ledChassisFanExists INTEGER,
                   ledChassisFanError INTEGER
                   }

       ledChassisFanIndex OBJECT-TYPE
                   SYNTAX  INTEGER (0..128)
                   ACCESS  read-only
                   STATUS  mandatory
                   DESCRIPTION
                   "Chassis fan LEDs table index."
                   ::= { chassisFanLEDsEntry 1 }

       ledChassisFanId OBJECT-TYPE
                   SYNTAX  INTEGER {
                     chassisfan1(1),
                     chassisfan2(2),
                     chassisfan3(3),
                     chassisfan4(4),
                     chassisfan5(5),
                     chassisfan6(6),
                     chassisfan7(7),
                     chassisfan8(8),
                     chassisfan9(9),
                     chassisfan10(10)
                   }
                   ACCESS  read-only
                   STATUS  mandatory
                   DESCRIPTION
                   "The numeric chassis fan ID."
                   ::= { chassisFanLEDsEntry 2 }

       ledChassisFanExists OBJECT-TYPE
                   SYNTAX  INTEGER {
                     false(0),
                     true(1)
                   }
                   ACCESS  read-only
                   STATUS  mandatory
                   DESCRIPTION
                   "Indicates whether the chassis fan specified exists or not."
                   ::= { chassisFanLEDsEntry 3 }

       ledChassisFanError OBJECT-TYPE
                   SYNTAX  INTEGER {
                     off(0),
                     on(1),
                     notAvailable(2)
                   }
                   ACCESS  read-only
                   STATUS  mandatory
                   DESCRIPTION
                   "Indicates whether the chassis fan error LED is on, off, or not available."
                   ::= { chassisFanLEDsEntry 4 }

     -- ********************************************************************************
     -- Power Module Fan Pack LEDs
     -- ********************************************************************************
     fanPackLEDs OBJECT IDENTIFIER ::= { leds 6 }

      fanPackLEDsTable OBJECT-TYPE
                    SYNTAX  SEQUENCE OF FanPackLEDsEntry
                    ACCESS  not-accessible
                    STATUS  deprecated
                    DESCRIPTION
                    "Table of fan pack LEDs information.  This table is
                    deprecated because the LEDs for the power modules' fans
                    are no longer on the fan packs, the LEDs are on the
                    power modules.
                    See the MIB tables, componentLEDsTable and
                    componentLEDsDetailsTable, for the power modules' LEDs.

                    NOTE: Fan packs are also referred to as Power Module Cooling Devices."
                    ::= { fanPackLEDs 1 }

       fanPackLEDsEntry OBJECT-TYPE
                     SYNTAX FanPackLEDsEntry
                     ACCESS  not-accessible
                     STATUS  deprecated
                     DESCRIPTION
                     "Fan Pack LEDs information entry"
                     INDEX { ledFanPackIndex }
                     ::= { fanPackLEDsTable 1 }


       FanPackLEDsEntry ::= SEQUENCE {
                   ledFanPackIndex INTEGER,
                   ledFanPackId INTEGER,

                   ledFanPackExists INTEGER,
                   ledFanPackError INTEGER
                   }

       ledFanPackIndex OBJECT-TYPE
                   SYNTAX  INTEGER (0..128)
                   ACCESS  read-only
                   STATUS  deprecated
                   DESCRIPTION
                   "Fan Pack LEDs table index."
                   ::= { fanPackLEDsEntry 1 }

       ledFanPackId OBJECT-TYPE
                   SYNTAX  INTEGER {
                      fanPack1(1),
                      fanPack2(2),
                      fanPack3(3),
                      fanPack4(4),
                      fanPack5(5),
                      fanPack6(6)
                   }
                   ACCESS  read-only
                   STATUS  deprecated
                   DESCRIPTION
                   "The numeric fan pack ID."
                   ::= { fanPackLEDsEntry 2 }

       ledFanPackExists OBJECT-TYPE
                   SYNTAX  INTEGER {
                     false(0),
                     true(1)
                   }
                   ACCESS  read-only
                   STATUS  deprecated
                   DESCRIPTION
                   "Indicates whether the fan pack specified exists or not."
                   ::= { fanPackLEDsEntry 3 }

       ledFanPackError OBJECT-TYPE
                   SYNTAX  INTEGER {
                     off(0),
                     on(1),
                     notAvailable(2)
                   }
                   ACCESS  read-only
                   STATUS  deprecated
                   DESCRIPTION
                   "Indicates whether the fan pack error LED is on or off."
                   ::= { fanPackLEDsEntry 4 }

    -- ********************************************************************************
    -- Power Management
    -- ********************************************************************************
    fuelGauge OBJECT IDENTIFIER ::= { monitors 10 }

     -- ********************************************************************************
     -- Fuel Gauge
     -- ********************************************************************************
     fuelGaugeInformation  OBJECT IDENTIFIER ::= { fuelGauge 1 }

      fuelGaugeTable OBJECT-TYPE
                   SYNTAX  SEQUENCE OF FuelGaugeEntry
                   ACCESS  not-accessible
                   STATUS  mandatory
                   DESCRIPTION
                   "Table of Fuel Gauge information."
                   ::= { fuelGaugeInformation 1 }

      fuelGaugeEntry OBJECT-TYPE
                   SYNTAX FuelGaugeEntry
                   ACCESS  not-accessible
                   STATUS  mandatory
                   DESCRIPTION
                   "Fuel Gauge entry"
                   INDEX { fuelGaugeIndex }
                   ::= { fuelGaugeTable 1 }

      FuelGaugeEntry ::= SEQUENCE {
                 fuelGaugeIndex INTEGER,
                 fuelGaugePowerDomainNumber INTEGER,
                 fuelGaugeStatus OCTET STRING,
                 fuelGaugePowerModules OCTET STRING,
                 fuelGaugePowerManagementPolicySetting INTEGER,
                 fuelGaugeTotalPower OCTET STRING,
                 fuelGaugeAllocatedPower OCTET STRING,
                 fuelGaugeRemainingPower OCTET STRING,
                 fuelGaugePowerInUsed OCTET STRING
                 }

      fuelGaugeIndex  OBJECT-TYPE
                 SYNTAX  INTEGER
                 ACCESS  read-only
                 STATUS  mandatory
                 DESCRIPTION
                 "Fuel Gauge Table Index."
                 ::= { fuelGaugeEntry 1 }

      fuelGaugePowerDomainNumber  OBJECT-TYPE
                 SYNTAX  INTEGER {
                   powerDomain1(1)
                 }
                 ACCESS  read-only
                 STATUS  mandatory
                 DESCRIPTION
                 "Fuel Gauge Table Power Domain Number."
                 ::= { fuelGaugeEntry 2 }

      fuelGaugeStatus  OBJECT-TYPE
                 SYNTAX  OCTET STRING
                 ACCESS  read-only
                 STATUS  mandatory
                 DESCRIPTION
                 "Fuel Gauge Table Status for the power domain.
                 The response will start out with a numeric value (0 = unknown,
                 1 = good, 2 = warning, and 3: bad), followed by a text message."
                 ::= { fuelGaugeEntry 3 }

      fuelGaugePowerModules  OBJECT-TYPE
                 SYNTAX  OCTET STRING
                 ACCESS  read-only
                 STATUS  mandatory
                 DESCRIPTION
                 "Fuel Gauge Table Power Module capacity in Watts in the power domain."
                 ::= { fuelGaugeEntry 4 }

      fuelGaugePowerManagementPolicySetting  OBJECT-TYPE
                 SYNTAX  INTEGER {
                   power-module-redundancy(0),
                   power-module-redundancy-throttle(1),
                   basic(2),
                   power-source-redundancy(3),
                   power-source-redundancy-throttle(4),
                   notApplicable(255)
                 }
                 ACCESS  read-only
                 STATUS  mandatory
                 DESCRIPTION
                 "Power Management Policy Setting for each power domain.

                 A new powerPolicyTable has been added which provides more detailed
                 information regarding a domains power policy information. This table
                 also has the capability to SET the power policy for a given domain.

                 Power Module Redundancy
                        
                        Intended for a single power source into the chassis where each
                        Power Module is on its own dedicated circuit. Maximum power is 
                        limited to one less than the number of Power Modules when more 
                        than one Power Module is present. One Power Module can fail 
                        without affecting compute node operation. Multiple Power Module 
                        failures can cause the chassis to power off. Note that some compute
                        nodes may not be allowed to power on if doing so would exceed the
                        policy power limit.
                              
                 Power Module Redundancy with Compute Nodes Throttling Allowed
                        
                        Very similar to Power Module Redundancy. This policy allows for a 
                        higher power limit; however, capable compute nodes may be allowed 
                        to throttle down if one Power Module fails.
                               
                 Basic Power Management
                        
                        Maximum power limit is higher than other policies and is limited 
                        only by the nameplate power of all the Power Modules combined. 
                        This is the least conservative approach, since it does not provide 
                        any protection for power source or Power Module failure. If any
                        single power supply fails, compute node and/or chassis operation 
                        may be affected.

                 Power Source Redundancy

                        Intended for dual power sources into the chassis. Maximum power is
                        limited to the capacity of half the number of installed power modules. 
                        This is the most conservative approach and is recommended when all power 
                        modules are installed. When the chassis is correctly wired with dual
                        power sources, one power source can fail without affecting compute
                        node server operation. Note that some compute nodes may not be allowed 
                        to power on if doing so would exceed the policy power limit.
                           
                 Power Source Redundancy with Compute Node Throttling Allowed
                        
                        Very similar to the Power Source Redundancy. This policy allows
                        for a higher power limit, however capable compute nodes may be allowed
                        to throttle down if one power source fails."
                 ::= { fuelGaugeEntry 6 }

       fuelGaugeTotalPower  OBJECT-TYPE
                 SYNTAX  OCTET STRING
                 ACCESS  read-only
                 STATUS  mandatory
                 DESCRIPTION
                 "This field displays the total available power for each power domain based on
                 installed power modules and the current Power Management Policy Setting."
                 ::= { fuelGaugeEntry 7 }

      fuelGaugeAllocatedPower  OBJECT-TYPE
                 SYNTAX  OCTET STRING
                 ACCESS  read-only
                 STATUS  mandatory
                 DESCRIPTION
                 "This field displays the power that has been reserved in each power domain."
                 ::= { fuelGaugeEntry 8 }

      fuelGaugeRemainingPower  OBJECT-TYPE
                 SYNTAX  OCTET STRING
                 ACCESS  read-only
                 STATUS  mandatory
                 DESCRIPTION
                 "This field displays the remaining power available in each domain.
                 Remaining Power = Total Power minus Power In Use"
                 ::= { fuelGaugeEntry 9 }

      fuelGaugePowerInUsed  OBJECT-TYPE
                 SYNTAX  OCTET STRING
                 ACCESS  read-only
                 STATUS  mandatory
                 DESCRIPTION
                 "This field displays the total power being used in each power domain."
                 ::= { fuelGaugeEntry 10 }

     -- ********************************************************************************
     -- Power Domain 
     -- ********************************************************************************
     powerDomain1  OBJECT IDENTIFIER ::= { fuelGauge 2 }

      powerDomain1Table OBJECT-TYPE
                   SYNTAX  SEQUENCE OF PowerDomain1Entry
                   ACCESS  not-accessible
                   STATUS  mandatory
                   DESCRIPTION
                   "Table of Power Domain 1."
                   ::= { powerDomain1 1}

      powerDomain1Entry OBJECT-TYPE
                   SYNTAX PowerDomain1Entry
                   ACCESS  not-accessible
                   STATUS  mandatory
                   DESCRIPTION
                   "Fuel Gauge entry"
                   INDEX { pd1Index }
                   ::= { powerDomain1Table 1 }

      PowerDomain1Entry ::= SEQUENCE {
                 pd1Index INTEGER,
                 pd1BayNumber OCTET STRING,
                 pd1BladePrimarySlot INTEGER,
                 pd1ModuleStatus INTEGER,
                 pd1ModuleName OCTET STRING,
                 pd1ModuleState INTEGER,
                 pd1ModuleAllocatedPowerCurrent OCTET STRING,
                 pd1ModuleAllocatedPowerMax OCTET STRING,
                 pd1ModuleAllocatedPowerMin OCTET STRING,
                 pd1ModuleCPUDutyCycles OCTET STRING,
                 pd1ModuleThrottle INTEGER,
                 pd1ModulePowerCapabilities INTEGER,
                 pd1ModuleMeasuredOrStatic INTEGER,
                 pd1TopologyPath OCTET STRING
                 }

      pd1Index  OBJECT-TYPE
                 SYNTAX  INTEGER
                 ACCESS  read-only
                 STATUS  mandatory
                 DESCRIPTION
                 "Power Domain 1 Table Index."
                 ::= { powerDomain1Entry 1 }

      pd1BayNumber  OBJECT-TYPE
                 SYNTAX  OCTET STRING
                 ACCESS  read-only
                 STATUS  mandatory
                 DESCRIPTION
                 "Power Domain 1 Table Bay Number.
                  The following Bay Number IDs are used:
                   notApplicable(1),
                   notApplicable(2),
                   fanPackBay1(3),
                   fanPackBay2(4),
                   fanPackBay3(5),
                   fanPackBay4(6),
                   fanPackBay5(7),
                   fanPackBay6(8),
                   chassisfanBay1(9),
                   chassisfanBay2(10),
                   chassisfanBay3(11),
                   chassisfanBay4(12),
                   chassisfanBay5(13),
                   chassisfanBay6(14),
                   chassisfanBay7(15),
                   chassisfanBay8(16),
                   chassisfanBay9(17),
                   chassisfanBay10(18),
                   managementModuleBay1(19),
                   managementModuleBay2(20),
                   ioModuleBay1(21),
                   ioModuleBay2(22),
                   ioModuleBay3(23),
                   ioModuleBay4(24),
                   serverBladeBay1(25),
                   serverBladeBay2(26),
                   serverBladeBay3(27),
                   serverBladeBay4(28),
                   serverBladeBay5(29),
                   serverBladeBay6(30),
                   serverBladeBay7(31),
                   serverBladeBay8(32),
                   serverBladeBay9(33),
                   serverBladeBay10(34),
                   serverBladeBay11(35),
                   serverBladeBay12(36),
                   serverBladeBay13(37),
                   serverBladeBay14(38),
                   notApplicable(39)"
                 ::= { powerDomain1Entry 2 }

      pd1BladePrimarySlot  OBJECT-TYPE
                 SYNTAX  INTEGER  {
                   no(0),
                   yes(1),
                   notApplicable(255)
                 }
                 ACCESS  read-only
                 STATUS  mandatory
                 DESCRIPTION
                 "Power Domain 1 Table Blade Primary Slot can be useful
                 when a server blade spans multiple slots (e.g. double wide or
                 triple wide).  For example if the blade is double wide and
                 is installed in slot 3 and 4.  3 is primary slot while 4 is not."
                 ::= { powerDomain1Entry 3 }

      pd1ModuleStatus  OBJECT-TYPE
                 SYNTAX  INTEGER  {
                   insufficientPower(0),
                   moduleIsThrottling(1),
                   moduleNotThrottling(2),
                   notApplicable(255)
                 }
                 ACCESS  read-only
                 STATUS  mandatory
                 DESCRIPTION
                 "Power Domain 1 Table Module Throttle Status."
                 ::= { powerDomain1Entry 4 }

      pd1ModuleName  OBJECT-TYPE
                 SYNTAX  OCTET STRING
                 ACCESS  read-only
                 STATUS  mandatory
                 DESCRIPTION
                 "Power Domain 1 Table Module Name."
                 ::= { powerDomain1Entry 5 }

      pd1ModuleState  OBJECT-TYPE
                 SYNTAX  INTEGER {
                   standby(0),
                   on(1),
                   notPresent(2),
                   off(3),
                   hibernate(4),
                   notApplicable(255)
                 }
                 ACCESS  read-only
                 STATUS  mandatory
                 DESCRIPTION
                 "Power Domain 1 Table Module State."
                 ::= { powerDomain1Entry 6 }

      pd1ModuleAllocatedPowerCurrent  OBJECT-TYPE
                 SYNTAX  OCTET STRING
                 ACCESS  read-only
                 STATUS  mandatory
                 DESCRIPTION
                 "Power Domain 1 Table Allocated Power Current indicates the current power
                 allocation for the module in Watts.

                 NOTE: When a server blade spans multiple slots (e.g. double wide or
                 triple wide), the current power allocation for the module is equally
                 divided among the slots."
                 ::= { powerDomain1Entry 7 }

      pd1ModuleAllocatedPowerMax  OBJECT-TYPE
                 SYNTAX  OCTET STRING
                 ACCESS  read-only
                 STATUS  mandatory
                 DESCRIPTION
                 "Power Domain 1 Table Allocated Power Max indicates the maximum power
                 allocation for the module in Watts.  It is indicative of the maximum
                 amount of power the module will consume in the domain when it is
                 fully populated with memory chips, expansion cards, etc.

                 NOTE: When a server blade spans multiple slots (e.g. double wide or
                 triple wide), the maximum power allocation for the module is equally
                 divided among the slots."
                 ::= { powerDomain1Entry 8 }

      pd1ModuleAllocatedPowerMin  OBJECT-TYPE
                 SYNTAX  OCTET STRING
                 ACCESS  read-only
                 STATUS  mandatory
                 DESCRIPTION
                 "Power Domain 1 Table Allocated Power Min indicates the minumum power
                 allocation for the module in Watts.  It is indicative of the minumum
                 power consumption of the component in the domain based on its
                 maximum throttle limit.

                 NOTE: When a server blade spans multiple slots (e.g. double wide or
                 triple wide), the minimum power allocation for the module is equally
                 divided among the slots."
                 ::= { powerDomain1Entry 9 }

      pd1ModuleCPUDutyCycles  OBJECT-TYPE
                 SYNTAX  OCTET STRING
                 ACCESS  read-only
                 STATUS  mandatory
                 DESCRIPTION
                 "Power Domain 1 Table Module CPUs Duty Cycles applies to blade
                 servers only.  It displays the duty cycle for each CPU on the blade
                 as a percentage.  Note that some blades do not report the CPU
                 duty cycles.  In this case, 'notApplicable' will be displayed.

                 NOTE: The CPU duty cycles are reported only on a primary slot when
                 a server blade spans multiple slots (e.g. double wide or
                 triple wide).  For example if the blade is double wide and
                 is installed in slot 3 and 4.  3 is primary slot while 4 is not.
                 The CPU duty cycles are reported on slot 3 while 'notApplicable'
                 is displayed for slot 4."
                 ::= { powerDomain1Entry 10 }

      pd1ModuleThrottle  OBJECT-TYPE
                 SYNTAX  INTEGER  {
                   no(0),
                   yes(1),
                   notApplicable(255)
                 }
                 ACCESS  read-only
                 STATUS  mandatory
                 DESCRIPTION
                 "Power Domain 1 Table Module Throttle indicates whether the
                 server blade may be allowed to throttle or not."
                 ::= { powerDomain1Entry 11 }

       pd1ModulePowerCapabilities  OBJECT-TYPE
                 SYNTAX  INTEGER {
                   noAbility(0),
                   staticPowerManagement(1),
                   fixedPowerManagement(2),
                   dynamicPowerManagement(3),
                   dynamicPowerMeasurement1(4),
                   dynamicPowerMeasurement2(5),
                   dynamicPowerMeasurementWithPowerCapping(6),
                   notApplicable(255)
                 }
                 ACCESS  read-only
                 STATUS  mandatory
                 DESCRIPTION
                 "Power Domain 1 Table Module Power Capabilities.

                 staticPowerManagement: the module with the static worst
                     case power values.
                 fixedPowermanagement: the module with the static power values but
                     ability to throttle.
                 dynamicPowerManagement: the module with power meter capability,
                     measurement enabled, but capping disabled.
                 dynamicPowerMeasurement1: the module with power meter capability,
                     measurement enabled, phase 1 only
                 dynamicPowerMeasurement2: the module with power meter capability,
                     measurement enabled, phase 2 or higher
                 dynamicPowerMeasurementWithPowerCapping: the module with power
                     meter capability, both measurement and capping enabled,
                     phase 2 or higher"
                 ::= { powerDomain1Entry 12 }

       pd1ModuleMeasuredOrStatic  OBJECT-TYPE
                 SYNTAX  INTEGER {
                   static(0),
                   measured(1),
                   notApplicable(255)
                 }
                 ACCESS  read-only
                 STATUS  mandatory
                 DESCRIPTION
                 "Power Domain 1 Table Module Measured Or Static."
                 ::= { powerDomain1Entry 13 }

       pd1TopologyPath  OBJECT-TYPE
                   SYNTAX  OCTET STRING  (SIZE (0..100))
                   ACCESS  read-only
                   STATUS  mandatory
                   DESCRIPTION
                   "The topology path for the component in this table. The chassis and each
                    installed component is represented by a hardware topology tree, where
                    each node in the tree represents a component. The path to a particular
                    component consists of one or more <component>,<instance> pairs, where
                    each successive pair is a child of the previous parent pair.

                    As an example, the root of the tree is the chassis and is represented
                    by the pair 'CHASSIS, 1'. This pair indicates the first instance of
                    the chassis. If a blade is inserted in slot 4 of the chassis, its
                    topology path is 'CHASSIS, 1, BLADE, 4'. With this format, the
                    components in the chassis can be determined along with their relative
                    hierarchy to each other.

                     CHASSIS,                0x01   Chassis
                     MM,                     0x02   Management Module
                     BLADE,                  0x03   Main system board of a blade
                     POWER,                  0x04   Power Supply, Power Module, etc
                     COOLING,                0x05   Fan, blower, or other cooling device
                     IO_MODULE,              0x06   Has I/O interface, i.e. - switch or bridge
                     MEDIA,                  0x07   Media device
                     PROCESSOR,              0x08   Any processor, processor module, etc
                     STORAGE,                0x09   Any type of storage device
                     EXPANSION,              0x0A   Expansion Card (not covered by more specific type)
                     MEMORY,                 0x0B   Any memory device, module, etc
                     MFRU,                   0x0C   Managed FRU Device
                     PANEL,                  0x0D   Any sort of panel device, such as a front panel
                     BLADE_EXPANSION_MODULE, 0x0E   Expansion option (BEM) such as PEU, BSE, etc
                     CARD_EXPANSION,         0x0F   Expansion card, ie. daughter card
                     CARD_HS_EXPANSION,      0x10   High Speed Expansion card, ie. daughter card
                     INTERPOSER,             0x11   Interposer device
                     CLOCK,                  0x12   Clock card
                     MUX,                    0x13   Mulitplexer card
                     ADDIN,                  0x14   cKVM card & other addin cards
                     STORAGE_MODULE,         0x15   Container of one or more Storage Devices
                     SYS_EXPANSION_CARD,     0x16   Management card
                     BATTERY,                0x17   A single battery
                     BATTERY_MODULE,         0x18   Container of one or more batteries
                     REAR_LED,               0x19   Rear LED card
                     MEMORY_BANK,            0x1A   Memory banks
                     AIR_FILTER,             0x1B   Filter mechanism (bezel)
                     SERIAL_PORT_MODULE,     0x1C   Container of one or more serial ports
                     PARENT,                 0x1D   Reference to parent for multi-parent support
                     PHY_PORT,               0x1E   Physical port
                     IO_EXPANDER,            0x1F   RAID card
                     CABLE,                  0x20   Cable/Interconnect
                     FAN_MUX                 0x29   Fan multiplexer card
                     PCI_EXPRESS,            0x32   PCI express card on (PEN)
                     FLASH_DIMM,             0x33   Used for SPD devices that matches the silkscreen of the DIMM slot
                     RACK,                   0x50   Rack
                     PLATFORM,               0x51   Generic Platform like rack mounted server/appliance
                     DATAPLEX,               0x52   DataPlex
                     OTHER,                  0x53   Other unknown etc.
                     PERIPHERAL_MODULE,      0x54 
                     SYSTEM_BOARD,           0x55   System board
                     PROCESSOR_MODULE,       0x56 
                     BACK_PANEL,             0x57 
                     POWER_SYSTEM_BOARD,     0x58 
                     STORAGE_BACKPLANE,      0x59   Drive back plane
                     PROC_BOARD,             0x5A   Holds 1 or more processors
                     POWER_DI,               0x5B   Power mgt / power distribution board
                     CHASSIS_BACK_PANEL,     0x5C 
                     SUB_CHASSIS,            0x5D 
                     OTHER_CHASSIS_BOARD,    0x5E 
                     DEVICE_MODULE,          0x5F 
                     REMOTE_DEVICE,          0x60   Remote mgt communication device
                     EXTERNAL_ENVIRONMENT,   0x61   Such as external temp sensor for outside box temps
                     PROC_MEMORY_MODULE,     0x62   Processors and memory on same module"
                   ::= { powerDomain1Entry 14 }


     -- ********************************************************************************
     -- Power Domain Power Trending
     -- ********************************************************************************
      powerDomain1PowerTrending  OBJECT IDENTIFIER ::= { powerDomain1 3 }

       pd1PowerTrendingPeriod  OBJECT-TYPE
                 SYNTAX  INTEGER  {
                        lastHour(0),
                        last6Hours(1),
                        last12Hours(2),
                        last24Hours(3)
                 }
                 ACCESS  read-write
                 STATUS  mandatory
                 DESCRIPTION
                 "Specify time period for power domain 1 power trending information
                 table view.

                 NOTE: This time period should be configured before displaying the
                 following Power Trending Information table for Power Domain."
                 ::= { powerDomain1PowerTrending 1 }

     -- ********************************************************************************
     -- Power Domain Power Trending Table
     -- ********************************************************************************
       pd1PowerTrendingSampleTable  OBJECT-TYPE
                SYNTAX  SEQUENCE OF Pd1PowerTrendingSampleEntry
                ACCESS  not-accessible
                STATUS  mandatory
                DESCRIPTION
                "Table of Power Domain 1 Power Trending Information."
                ::= { powerDomain1PowerTrending 10 }

       pd1PowerTrendingSampleEntry OBJECT-TYPE
                SYNTAX Pd1PowerTrendingSampleEntry
                ACCESS  not-accessible
                STATUS  mandatory
                DESCRIPTION
                "Power Domain 1 Power Trending Sample entry."
                INDEX { pd1PowerTrendingSampleIndex }
                ::= { pd1PowerTrendingSampleTable 1 }

       Pd1PowerTrendingSampleEntry ::= SEQUENCE {
                pd1PowerTrendingSampleIndex INTEGER,
                pd1PowerTrendingSampleTimeStamp OCTET STRING,
                pd1PowerTrendingSampleAve OCTET STRING
                }

       pd1PowerTrendingSampleIndex  OBJECT-TYPE
                SYNTAX  INTEGER
                ACCESS  read-only
                STATUS  mandatory
                DESCRIPTION
                "Power Domain 1 Power Trending Sample Table Index."
                ::= { pd1PowerTrendingSampleEntry 1 }

       pd1PowerTrendingSampleTimeStamp  OBJECT-TYPE
                SYNTAX  OCTET STRING
                ACCESS  read-only
                STATUS  mandatory
                DESCRIPTION
                "Power Domain 1 Power Trending Sample Table Timestamp."
                ::= { pd1PowerTrendingSampleEntry 2 }

       pd1PowerTrendingSampleAve  OBJECT-TYPE
                SYNTAX  OCTET STRING
                ACCESS  read-only
                STATUS  mandatory
                DESCRIPTION
                "Power Domain 1 Power Trending Table Average Power."
                ::= { pd1PowerTrendingSampleEntry 3 }

     -- ******************************************************************************
     -- Power Mgmt Module Information
     -- ******************************************************************************
     moduleInformation  OBJECT IDENTIFIER ::= { fuelGauge 4 }

      bladeDetails  OBJECT IDENTIFIER ::= { moduleInformation 1 }

       bladeDetailsTable OBJECT-TYPE
                   SYNTAX  SEQUENCE OF BladeDetailsEntry
                   ACCESS  not-accessible
                   STATUS  mandatory
                   DESCRIPTION
                   "Table of Blade Module Details."
                   ::= { bladeDetails 1}

       bladeDetailsEntry OBJECT-TYPE
                   SYNTAX BladeDetailsEntry
                   ACCESS  not-accessible
                   STATUS  mandatory
                   DESCRIPTION
                   "Blade Module Details entry."
                   INDEX { bladeDetailsIndex }
                   ::= { bladeDetailsTable 1 }

       BladeDetailsEntry ::= SEQUENCE {
                 bladeDetailsIndex INTEGER,
                 bladeDetailsId INTEGER,
                 bladeDetailsMaxPowerConfig INTEGER,
                 bladeDetailsEffectiveClockRate OCTET STRING,
                 bladeDetailsMaximumClockRate OCTET STRING,
                 bladeDetailsPowerSaverMode INTEGER,
                 bladeDetailsDynamicPowerSaver INTEGER,
                 bladeDetailsDynamicPowerFavorPerformanceOverPower INTEGER,
                 bladeDetailsPowerControl INTEGER,
                 bladeDetailsPcapMin OCTET STRING,
                 bladeDetailsPcapGuaranteedMin OCTET STRING,
                 bladeDetailsPcapMax OCTET STRING
                 }

       bladeDetailsIndex  OBJECT-TYPE
                 SYNTAX  INTEGER
                 ACCESS  read-only
                 STATUS  mandatory
                 DESCRIPTION
                 "Blade Module Details Table Index."
                 ::= { bladeDetailsEntry 1 }

       bladeDetailsId  OBJECT-TYPE
                   SYNTAX  INTEGER {
                       blade1(1),
                       blade2(2),
                       blade3(3),
                       blade4(4),
                       blade5(5),
                       blade6(6),
                       blade7(7),
                       blade8(8),
                       blade9(9),
                       blade10(10),
                       blade11(11),
                       blade12(12),
                       blade13(13),
                       blade14(14)
                     }
                   ACCESS  read-only
                   STATUS  mandatory
                   DESCRIPTION
                   "Blade Module Details Table Blade Id."
                 ::= { bladeDetailsEntry 2 }

       bladeDetailsMaxPowerConfig  OBJECT-TYPE
                 SYNTAX  INTEGER
                 ACCESS  read-write
                 STATUS  mandatory
                 DESCRIPTION
                 "Blade Module Details Table Maximum Power Configuration.
                 Allow the user to set the maximum power that can be used by the blade. This
                 function is also known as power capping.
                 Blade must be powered on to set this value.

                 If the value of maximum power config is zero, it means the blade doesn't
                 support the power capping feature"
                 ::= { bladeDetailsEntry 3 }

       bladeDetailsEffectiveClockRate  OBJECT-TYPE
                 SYNTAX  OCTET STRING
                 ACCESS  read-only
                 STATUS  mandatory
                 DESCRIPTION
                 "Blade Module Details Table Effective CPU Clock Rate applies to DPM
                 blades only.  It displays processor's effective clock rate based
                 on sample interval.  Note that some blades do not effective
                 clock rate.  In this case, 'notApplicable' will be displayed.

                 NOTE: The effective clock rate are reported only on a primary slot when
                 a server blade spans multiple slots (e.g. double wide or
                 triple wide).  For example if the blade is double wide and
                 is installed in slot 3 and 4.  3 is primary slot while 4 is not.
                 The effective clock rate are reported on slot 3 while 'notApplicable'
                 is displayed for slot 4."
                 ::= { bladeDetailsEntry 4 }

       bladeDetailsMaximumClockRate  OBJECT-TYPE
                 SYNTAX  OCTET STRING
                 ACCESS  read-only
                 STATUS  mandatory
                 DESCRIPTION
                 "Blade Module Details Table Maximum CPU Clock Rate applies to DPM
                 blades only.  It displays processor's maximum clock rate based
                 on sample interval.  Note that some blades do not maximum
                 clock rate.  In this case, 'notApplicable' will be displayed.

                 NOTE: The maximum clock rate are reported only on a primary slot when
                 a server blade spans multiple slots (e.g. double wide or
                 triple wide).  For example if the blade is double wide and
                 is installed in slot 3 and 4.  3 is primary slot while 4 is not.
                 The maximum clock rate are reported on slot 3 while 'notApplicable'
                 is displayed for slot 4."
                 ::= { bladeDetailsEntry 5 }

       bladeDetailsPowerSaverMode OBJECT-TYPE
                 SYNTAX  INTEGER {
                         disable(0),
                         enable(1),
                         notApplicable(255)
                 }
                 ACCESS  read-write
                 STATUS  mandatory
                 DESCRIPTION
                 "When enabled, the static low power saver mode allows the blade to selectively
                 alter its operating voltage and frequency to reduce power consumption.
                 This feature is not available on all blade types.  Please refer to the blade documentation for details.
                 If a blade does not support the static low power saver mode, this object will return notApplicable (255).

                 Under certain rare circumstances, the enabling of the static low power saver mode
                 may not complete successfully due to interactions with other
                 blade functions, such as BIOS. Therefore, it is highly recommended that
                 the user perform a GET of this object after performing a SET, in order
                 to verify the completion of the intended operation.

                 NOTE: enabling this object will disable bladeDetailsDynamicPowerSaver if its not already disabled."
                 ::= { bladeDetailsEntry 6 }

       bladeDetailsDynamicPowerSaver OBJECT-TYPE
                 SYNTAX  INTEGER {
                         disable(0),
                         enable(1),
                         notApplicable(255)
                 }
                 ACCESS  read-write
                 STATUS  mandatory
                 DESCRIPTION
                 "When enabled, Dynamic Power Saver allows the voltage and frequency of the CPUs on the blade
                 to be controlled based on how busy the CPU is.  This feature is not available on all blade types.
                 Please refer to the blade documentation for details.  If a blade does not support the dynamic power
                 saver, this object will return notApplicable (255).

                 Under certain rare circumstances, the enabling of the dynamic power saver may not complete
                 successfully due to interactions with other blade functions, such as BIOS. Therefore, it is
                 highly recommended that the user perform a GET of this object after performing a SET, in order
                 to verify the completion of the intended operation.

                 NOTE: enabling this object will disable bladeDetailsPowerSaverMode if its not already disabled."
                 ::= { bladeDetailsEntry 7 }

       bladeDetailsDynamicPowerFavorPerformanceOverPower OBJECT-TYPE
                 SYNTAX  INTEGER {
                         disable(0),
                         enable(1),
                         notApplicable(255)
                 }
                 ACCESS  read-write
                 STATUS  mandatory
                 DESCRIPTION
                 "When enabled, Dynamic Power Favor Performance Over Power supports a max performance mode that pushes the
                 system past its nominal CPU frequency when CPU and memory utilization implies it would help and the
                 system allows it.  Dynamic Power Performance Over Power can be active on the blade only after Dynamic
                 Power Saver is enabled.  This feature is not available on all blade types.  Please refer to the
                 blade documentation for details.  If a blade does not support the dynamic power saver, this object
                 will return notApplicable (255).

                 Under certain rare circumstances, the enabling of the dynamic power favor performance over power
                 may not complete successfully due to interactions with other blade functions, such as BIOS.
                 Therefore, it is highly recommended that the user perform a GET of this object after performing a SET,
                 in order to verify the completion of the intended operation."
                 ::= { bladeDetailsEntry 8 }

       bladeDetailsPowerControl OBJECT-TYPE
                 SYNTAX  INTEGER {
                         none(0),
                         measurement(1),
                         measurementpcap(2),
                         psave(3),
                         measurementpsave(4),
                         measurementpcappsave(5),
                         notApplicable(255)
                 }
                 ACCESS  read-write
                 STATUS  mandatory
                 DESCRIPTION
                 "This object is used to get or set the power control setting on a blade. 

                 If dynamic power mgmt is not supported on a blade, notApplicable(255) will be returned.

                 This will set the power control setting on all slots of the multiwide blade. The 
                 same can be used if the blade is single wide."
                 ::= { bladeDetailsEntry 9 }

       bladeDetailsPcapMin  OBJECT-TYPE
                 SYNTAX  OCTET STRING
                 ACCESS  read-only
                 STATUS  mandatory
                 DESCRIPTION
                 "Blade Module Details Table power capping Minimum value in watts.
                 The blade must support the advanced power management feature.

                 If the value of Pcap Min is 'notApplicable', it means the blade doesn't
                 support the power capping feature.

                 If the value of Pcap Min is 'notAvailable', it means the data
                 could not be obtained."
                 ::= { bladeDetailsEntry 10 }

       bladeDetailsPcapGuaranteedMin  OBJECT-TYPE
                 SYNTAX  OCTET STRING
                 ACCESS  read-only
                 STATUS  mandatory
                 DESCRIPTION
                 "Blade Module Details Table power capping Guaranteed Minimum value in watts.
                 The blade must support the advanced power management feature.

                 If the value of Pcap Guaranteed Min is 'notApplicable', it means the blade doesn't
                 support the power capping feature.

                 If the value of Pcap GuaranteedMin is 'notAvailable', it means the data
                 could not be obtained."
                 ::= { bladeDetailsEntry 11 }

       bladeDetailsPcapMax  OBJECT-TYPE
                 SYNTAX  OCTET STRING
                 ACCESS  read-only
                 STATUS  mandatory
                 DESCRIPTION
                 "Blade Module Details Table power capping Maximum value in watts.
                 The blade must support the advanced power management feature.

                 If the value is '<max1> Watts,<max2> Watts', which means,
                 - if bladeDetailsDynamicPowerSaver is enabled, it is <max2>
                 - otherwise it is <max1>

                 If the value of Pcap Max is 'notApplicable', it means the blade doesn't
                 support the power capping feature.

                 If the value of Pcap Min is 'notAvailable', it means the data
                 could not be obtained."
                 ::= { bladeDetailsEntry 12 }

     -- ******************************************************************************
     -- Power Mgmt Blade Power Trending
     -- ******************************************************************************
       bladePowerTrending  OBJECT IDENTIFIER ::= { bladeDetails 3 }

        bladePowerTrendingPeriod  OBJECT-TYPE
                 SYNTAX  INTEGER  {
                        lastHour(0),
                        last6Hours(1),
                        last12Hours(2),
                        last24Hours(3)
                 }
                 ACCESS  read-write
                 STATUS  mandatory
                 DESCRIPTION
                 "Specify time period for blade module power trending information table view.

                 NOTE: This time period should be configured before displaying the
                 following Power Trending Information table for Blade Module.
                 Since the power trending data is constantly being computed and saved in the
                 management application database, some queries of the bladePowerTrendingSampleTable
                 may not provide information for a very short window of time.
                 If the table returns empty, please wait a short period and retry the query."

                 ::= { bladePowerTrending 1 }

        bladePowerTrendingBladeId  OBJECT-TYPE
                   SYNTAX  INTEGER {
                       blade1(1),
                       blade2(2),
                       blade3(3),
                       blade4(4),
                       blade5(5),
                       blade6(6),
                       blade7(7),
                       blade8(8),
                       blade9(9),
                       blade10(10),
                       blade11(11),
                       blade12(12),
                       blade13(13),
                       blade14(14)
                     }
                   ACCESS  read-write
                   STATUS  mandatory
                   DESCRIPTION
                   "Blade Module Power Trending Blade Id.

                   NOTE: The Blade Id should be configured before displaying the
                   bladePowerTrendingTable."
                   ::= { bladePowerTrending 2 }

        bladePowerTrendingTopologyPath  OBJECT-TYPE
                   SYNTAX  OCTET STRING  (SIZE (0..100))
                   ACCESS  read-write
                   STATUS  mandatory
                   DESCRIPTION
                   "The topology Path is a location identifier for a blade. The chassis and each
                    installed blade is represented by a hardware topology tree, where
                    each node in the tree represents a blade. The path to a particular
                    blade consists of one or more <blade>,<instance> pairs, where
                    each successive pair is a child of the previous parent pair.

                    This topology path is used to identify blades such as blade storage devices.
                    Some examples. A storage blade with a controller card plugged into slot 1
                    topology location would be represented as :
                    010103010301--> Storage Controller card #1 of Sub-Chassis #1

                    A storage blade with a controller card plugged into slot 2
                    topology location would be represented as :
                    010103010302--> Storage Controller card #2 of Sub-Chassis #1 "
                   ::= { bladePowerTrending 3 }

     -- ******************************************************************************
     -- Power Mgmt Blade Power Trending Table
     -- ******************************************************************************

        bladePowerTrendingSampleTable  OBJECT-TYPE
                SYNTAX  SEQUENCE OF BladePowerTrendingSampleEntry
                ACCESS  not-accessible
                STATUS  mandatory
                DESCRIPTION
                "Table of Blade Module Power Trending Information.
                 Since the power trending data is constantly being computed and saved in the
                 management application database, some queries of this table may not provide
                 information for a very short window of time.
                 If the table data returns empty,please wait a short period and retry the query."
                ::= { bladePowerTrending 10 }

        bladePowerTrendingSampleEntry OBJECT-TYPE
                SYNTAX  BladePowerTrendingSampleEntry
                ACCESS  not-accessible
                STATUS  mandatory
                DESCRIPTION
                "Blade Module Power Trending Sample entry."
                INDEX { bladePowerTrendingSampleIndex }
                ::= { bladePowerTrendingSampleTable 1 }

        BladePowerTrendingSampleEntry ::= SEQUENCE {
                bladePowerTrendingSampleIndex INTEGER,
                bladePowerTrendingSampleId INTEGER,
                bladePowerTrendingSampleTimeStamp OCTET STRING,
                bladePowerTrendingSampleMax OCTET STRING,
                bladePowerTrendingSampleMin OCTET STRING,
                bladePowerTrendingSampleAve OCTET STRING,
                bladePowerTrendingSampleTopologyId OCTET STRING
                }

        bladePowerTrendingSampleIndex  OBJECT-TYPE
                SYNTAX  INTEGER
                ACCESS  read-only
                STATUS  mandatory
                DESCRIPTION
                "Blade Module Power Trending Sample Table Index."
                ::= { bladePowerTrendingSampleEntry 1 }

        bladePowerTrendingSampleId  OBJECT-TYPE
                   SYNTAX  INTEGER {
                       blade1(1),
                       blade2(2),
                       blade3(3),
                       blade4(4),
                       blade5(5),
                       blade6(6),
                       blade7(7),
                       blade8(8),
                       blade9(9),
                       blade10(10),
                       blade11(11),
                       blade12(12),
                       blade13(13),
                       blade14(14)
                     }
                   ACCESS  read-only
                   STATUS  mandatory
                   DESCRIPTION
                   "Blade Module Power Trending Sample Table Blade Id.
                    If the blade is defined using a topology location
                    by using the scalar bladePowerTrendingTopologyPath, a
                    zero will be displayed in the bladePowerTrendingSampleId."
                   ::= { bladePowerTrendingSampleEntry 2 }

        bladePowerTrendingSampleTimeStamp  OBJECT-TYPE
                SYNTAX  OCTET STRING
                ACCESS  read-only
                STATUS  mandatory
                DESCRIPTION
                "Blade Module Power Trending Sample Table  Timestamp."
                ::= { bladePowerTrendingSampleEntry 3 }

        bladePowerTrendingSampleMax  OBJECT-TYPE
                SYNTAX  OCTET STRING
                ACCESS  read-only
                STATUS  mandatory
                DESCRIPTION
                "Blade Module Power Trending Sample Table Maximum Power."
                ::= { bladePowerTrendingSampleEntry 4 }

        bladePowerTrendingSampleMin  OBJECT-TYPE
                SYNTAX  OCTET STRING
                ACCESS  read-only
                STATUS  mandatory
                DESCRIPTION
                "Blade Module Power Trending Sample Table Minimum Power."
                ::= { bladePowerTrendingSampleEntry 5 }

        bladePowerTrendingSampleAve  OBJECT-TYPE
                SYNTAX  OCTET STRING
                ACCESS  read-only
                STATUS  mandatory
                DESCRIPTION
                "Blade Module Power Trending Sample Table Average Power."
                ::= { bladePowerTrendingSampleEntry 6 }

        bladePowerTrendingSampleTopologyId  OBJECT-TYPE
                SYNTAX  OCTET STRING
                ACCESS  read-only
                STATUS  mandatory
                DESCRIPTION
                "Blade module topology path. This field will have a
                 topology location when a blade is a storage blade or
                 a blade defined with a sub chassis. If the blade is defined
                 with a primary slot location by using the scalar
                 bladePowerTrendingBladeId, 'not applicable' will be
                 displayed in the bladePowerTrendingSampleTopologyId."


                ::= { bladePowerTrendingSampleEntry 7 }


     -- ******************************************************************************
     -- Power Mgmt Switch Power Trending 
     -- ******************************************************************************
      switchDetails  OBJECT IDENTIFIER ::= { moduleInformation 2 }

       switchPowerTrending  OBJECT IDENTIFIER ::= { switchDetails 3 }

        switchPowerTrendingPeriod  OBJECT-TYPE
                 SYNTAX  INTEGER  {
                        lastHour(0),
                        last6Hours(1),
                        last12Hours(2),
                        last24Hours(3)
                 }
                 ACCESS  read-write
                 STATUS  mandatory
                 DESCRIPTION
                 "Specify time period for switch module power trending information table view.

                 NOTE: This time period should be configured before displaying the
                 following Power Trending Information table for Switch Module."
                 ::= { switchPowerTrending 1 }

        switchPowerTrendingSwitchId  OBJECT-TYPE
                   SYNTAX  INTEGER {
                        module1(1),
                        module2(2),
                        module3(3),
                        module4(4)
                     }
                   ACCESS  read-write
                   STATUS  mandatory
                   DESCRIPTION
                   "Switch Module Power Trending Switch Id.

                   NOTE: The Switch Id should be configured before displaying the
                   switchPowerTrendingTable."
                   ::= { switchPowerTrending 2 }

     -- ******************************************************************************
     -- Power Mgmt Switch Power Trending Table 
     -- ******************************************************************************
       switchPowerTrendingSampleTable  OBJECT-TYPE
                SYNTAX  SEQUENCE OF SwitchPowerTrendingSampleEntry
                ACCESS  not-accessible
                STATUS  mandatory
                DESCRIPTION
                "Table of Switch Module Power Trending Information."
                ::= { switchPowerTrending 10 }

       switchPowerTrendingSampleEntry OBJECT-TYPE
                SYNTAX  SwitchPowerTrendingSampleEntry
                ACCESS  not-accessible
                STATUS  mandatory
                DESCRIPTION
                "Switch Module Power Trending Sample entry."
                INDEX { switchPowerTrendingSampleIndex }
                ::= { switchPowerTrendingSampleTable 1 }

       SwitchPowerTrendingSampleEntry ::= SEQUENCE {
                switchPowerTrendingSampleIndex INTEGER,
                switchPowerTrendingSampleId INTEGER,
                switchPowerTrendingSampleTimeStamp OCTET STRING,
                switchPowerTrendingSampleMax OCTET STRING,
                switchPowerTrendingSampleMin OCTET STRING,
                switchPowerTrendingSampleAve OCTET STRING
                }

       switchPowerTrendingSampleIndex  OBJECT-TYPE
                SYNTAX  INTEGER
                ACCESS  read-only
                STATUS  mandatory
                DESCRIPTION
                "Switch Module Power Trending Sample Table Index."
                ::= { switchPowerTrendingSampleEntry 1 }

       switchPowerTrendingSampleId  OBJECT-TYPE
                   SYNTAX  INTEGER {
                       module1(1),
                       module2(2),
                       module3(3),
                       module4(4),
                       module5(5),
                       module6(6),
                       module7(7),
                       module8(8),
                       module9(9),
                       module10(10)
                     }
                   ACCESS  read-only
                   STATUS  mandatory
                   DESCRIPTION
                   "Switch Module Power Trending Sample Table Switch Id."
                   ::= { switchPowerTrendingSampleEntry 2 }

       switchPowerTrendingSampleTimeStamp  OBJECT-TYPE
                SYNTAX  OCTET STRING
                ACCESS  read-only
                STATUS  mandatory
                DESCRIPTION
                "Switch Module Power Trending Sample Table  Timestamp."
                ::= { switchPowerTrendingSampleEntry 3 }

       switchPowerTrendingSampleMax  OBJECT-TYPE
                SYNTAX  OCTET STRING
                ACCESS  read-only
                STATUS  mandatory
                DESCRIPTION
                "Switch Module Power Trending Sample Table Maximum Power."
                ::= { switchPowerTrendingSampleEntry 4 }

       switchPowerTrendingSampleMin  OBJECT-TYPE
                SYNTAX  OCTET STRING
                ACCESS  read-only
                STATUS  mandatory
                DESCRIPTION
                "Switch Module Power Trending Sample Table Minimum Power."
                ::= { switchPowerTrendingSampleEntry 5 }

       switchPowerTrendingSampleAve  OBJECT-TYPE
                SYNTAX  OCTET STRING
                ACCESS  read-only
                STATUS  mandatory
                DESCRIPTION
                "Switch Module Power Trending Sample Table Average Power."
                ::= { switchPowerTrendingSampleEntry 6 }


     -- ******************************************************************************
     -- Power Mgmt Chassis Fans Power Trending 
     -- ******************************************************************************
      chassisFanDetails  OBJECT IDENTIFIER ::= { moduleInformation 3 }

       chassisFanPowerTrending  OBJECT IDENTIFIER ::= { chassisFanDetails 3 }

        chassisFanPowerTrendingPeriod  OBJECT-TYPE
                 SYNTAX  INTEGER  {
                        lastHour(0),
                        last6Hours(1),
                        last12Hours(2),
                        last24Hours(3)
                 }
                 ACCESS  read-write
                 STATUS  mandatory
                 DESCRIPTION
                 "Specify time period for chassis fan module power trending information table view.

                 NOTE: This time period should be configured before displaying the
                 following Power Trending Information table for chassis fan module."
                 ::= { chassisFanPowerTrending 1 }

        chassisFanPowerTrendingId  OBJECT-TYPE
                   SYNTAX  INTEGER {
                       chassisFan1(1),
                       chassisFan2(2),
                       chassisFan3(3),
                       chassisFan4(4),
                       chassisFan5(5),
                       chassisFan6(6),
                       chassisFan7(7),
                       chassisFan8(8),
                       chassisFan9(9),
                       chassisFan10(10)
                     }
                   ACCESS  read-write
                   STATUS  mandatory
                   DESCRIPTION
                   "Chass fan mModule power trending fan ID.

                   NOTE: The ID should be configured before displaying the chassisFanPowerTrendingTable."
                   ::= { chassisFanPowerTrending 2 }

     -- ******************************************************************************
     -- Power Mgmt Chassis Fans Power Trending Table 
     -- ******************************************************************************
       chassisFanPowerTrendingSampleTable  OBJECT-TYPE
                SYNTAX  SEQUENCE OF ChassisFanPowerTrendingSampleEntry
                ACCESS  not-accessible
                STATUS  mandatory
                DESCRIPTION
                "Table of chassis fan Module Power Trending Information."
                ::= { chassisFanPowerTrending 10 }

       chassisFanPowerTrendingSampleEntry OBJECT-TYPE
                SYNTAX  ChassisFanPowerTrendingSampleEntry
                ACCESS  not-accessible
                STATUS  mandatory
                DESCRIPTION
                "Chassis fan Module Power Trending Sample entry."
                INDEX { chassisFanPowerTrendingSampleIndex }
                ::= { chassisFanPowerTrendingSampleTable 1 }

       ChassisFanPowerTrendingSampleEntry ::= SEQUENCE {
                chassisFanPowerTrendingSampleIndex INTEGER,
                chassisFanPowerTrendingSampleId INTEGER,
                chassisFanPowerTrendingSampleTimeStamp OCTET STRING,
                chassisFanPowerTrendingSampleMax OCTET STRING,
                chassisFanPowerTrendingSampleMin OCTET STRING,
                chassisFanPowerTrendingSampleAve OCTET STRING
                }

       chassisFanPowerTrendingSampleIndex  OBJECT-TYPE
                SYNTAX  INTEGER
                ACCESS  read-only
                STATUS  mandatory
                DESCRIPTION
                "Chassis fan Module Power Trending Sample Table Index."
                ::= { chassisFanPowerTrendingSampleEntry 1 }

       chassisFanPowerTrendingSampleId  OBJECT-TYPE
                   SYNTAX  INTEGER {
                       chassisFan1(1),
                       chassisFan2(2),
                       chassisFan3(3),
                       chassisFan4(4),
                       chassisFan5(5),
                       chassisFan6(6),
                       chassisFan7(7),
                       chassisFan8(8),
                       chassisFan9(9),
                       chassisFan10(10)
                     }
                   ACCESS  read-only
                   STATUS  mandatory
                   DESCRIPTION
                   "Chassis fan Module Power Trending Sample Table Id."
                   ::= { chassisFanPowerTrendingSampleEntry 2 }

       chassisFanPowerTrendingSampleTimeStamp  OBJECT-TYPE
                SYNTAX  OCTET STRING
                ACCESS  read-only
                STATUS  mandatory
                DESCRIPTION
                "Chassis fan Module Power Trending Sample Table Timestamp."
                ::= { chassisFanPowerTrendingSampleEntry 3 }

       chassisFanPowerTrendingSampleMax  OBJECT-TYPE
                SYNTAX  OCTET STRING
                ACCESS  read-only
                STATUS  mandatory
                DESCRIPTION
                "Chassis fan Module Power Trending Sample Table Maximum Power."
                ::= { chassisFanPowerTrendingSampleEntry 4 }

       chassisFanPowerTrendingSampleMin  OBJECT-TYPE
                SYNTAX  OCTET STRING
                ACCESS  read-only
                STATUS  mandatory
                DESCRIPTION
                "Chassis fan Module Power Trending Sample Table Minimum Power."
                ::= { chassisFanPowerTrendingSampleEntry 5 }

       chassisFanPowerTrendingSampleAve  OBJECT-TYPE
                SYNTAX  OCTET STRING
                ACCESS  read-only
                STATUS  mandatory
                DESCRIPTION
                "Chassis fan Module Power Trending Sample Table Average Power."
                ::= { chassisFanPowerTrendingSampleEntry 6 }

      -- ******************************************************************************
      -- Chassis Global Information
      -- ******************************************************************************

     chassisInformation  OBJECT IDENTIFIER ::= { fuelGauge 5 }

      chassisConfiguration  OBJECT IDENTIFIER ::= { chassisInformation 1 }

       chassisTotalDCPowerAvailable  OBJECT-TYPE
                SYNTAX  OCTET STRING
                ACCESS  read-only
                STATUS  mandatory
                DESCRIPTION
                "Chassis total DC power available, which displays the total DC power available
                for the entire chassis. It is the sum of the two power domains."
                ::= { chassisConfiguration 1 }

       chassisTotalPowerInUsed  OBJECT-TYPE
                SYNTAX  OCTET STRING
                ACCESS  read-only
                STATUS  mandatory
                DESCRIPTION
                "Chassis total power being used, which displays the total power
                being consumed by all modules in the chassis. It also includes power
                consumed by the blowers (chassis cooling devices) for the chassis."
                ::= { chassisConfiguration 2 }

       chassisTotalThermalOutput  OBJECT-TYPE
                SYNTAX  OCTET STRING
                ACCESS  read-only
                STATUS  mandatory
                DESCRIPTION
                "Chassis total thermal output, which displays the thermal output
                (load) in BTUs per hour. It is calculated based on the total input
                power in use. (1 Watt = 3.412 BTU/hour)."
                ::= { chassisConfiguration 3 }

       chassisPowerService OBJECT-TYPE
                 SYNTAX  INTEGER {
                     volt110(1),
                     volt220(2),
                     notAvailable(255)
                 }
                 ACCESS  read-only
                 STATUS  deprecated
                 DESCRIPTION
                 "The chassis power service mode.

                 NOTE: This MIB object is for BCS only.

                 This object has been deprecated. See the object,
                 powerModuleDescription, for similar information."
                 ::= { chassisConfiguration 5 }

      -- ******************************************************************************
      -- Chassis Power Trending Information
      -- ******************************************************************************
      chassisPowerTrending  OBJECT IDENTIFIER ::= { chassisInformation 3 }

       chassisPowerTrendingPeriod  OBJECT-TYPE
                 SYNTAX  INTEGER  {
                        lastHour(0),
                        last6Hours(1),
                        last12Hours(2),
                        last24Hours(3)
                 }
                 ACCESS  read-write
                 STATUS  mandatory
                 DESCRIPTION
                 "Specify time period of power trending information.
                 NOTE: This time period should be configured before displaying the
                 following Power Trending Information table for Chassis."
                 ::= { chassisPowerTrending 1 }

       chassisPowerTrendingSampleTable  OBJECT-TYPE
                SYNTAX  SEQUENCE OF ChassisPowerTrendingSampleEntry
                ACCESS  not-accessible
                STATUS  mandatory
                DESCRIPTION
                "Table of Chassis Power Trending Sample Information in specified time period."
                ::= { chassisPowerTrending 10 }

       chassisPowerTrendingSampleEntry OBJECT-TYPE
                SYNTAX ChassisPowerTrendingSampleEntry
                ACCESS  not-accessible
                STATUS  mandatory
                DESCRIPTION
                "Chassis Power Trending Sample entry in specified time period."
                INDEX { chassisPowerTrendingSampleIndex }
                ::= { chassisPowerTrendingSampleTable 1 }

       ChassisPowerTrendingSampleEntry ::= SEQUENCE {
                chassisPowerTrendingSampleIndex INTEGER,
                chassisPowerTrendingSampleTimeStamp OCTET STRING,
                chassisPowerTrendingSampleAve OCTET STRING
                }

       chassisPowerTrendingSampleIndex  OBJECT-TYPE
                SYNTAX  INTEGER
                ACCESS  read-only
                STATUS  mandatory
                DESCRIPTION
                "Chassis Power Trending Sample Index in specified time period."
                ::= { chassisPowerTrendingSampleEntry 1 }

       chassisPowerTrendingSampleTimeStamp  OBJECT-TYPE
                SYNTAX  OCTET STRING
                ACCESS  read-only
                STATUS  mandatory
                DESCRIPTION
                "Chassis Power Trending Sample Timestamp in specified time period."
                ::= { chassisPowerTrendingSampleEntry 2 }

       chassisPowerTrendingSampleAve  OBJECT-TYPE
                SYNTAX  OCTET STRING
                ACCESS  read-only
                STATUS  mandatory
                DESCRIPTION
                "Chassis Power Trending Sample Average Power in specified time period."
                ::= { chassisPowerTrendingSampleEntry 3 }

      -- ******************************************************************************
      -- Chassis Thermal Trending Information
      -- ******************************************************************************
      chassisThermalTrending  OBJECT IDENTIFIER ::= { chassisInformation 5 }

       chassisThermalTrendingPeriod  OBJECT-TYPE
                 SYNTAX  INTEGER  {
                        lastHour(0),
                        last6Hours(1),
                        last12Hours(2),
                        last24Hours(3)
                 }
                 ACCESS  read-write
                 STATUS  mandatory
                 DESCRIPTION
                 "Specify time period of thermal trending information.
                 NOTE: This time period should be configured before displaying the
                 following Thermal Trending Information table for Chassis."
                 ::= { chassisThermalTrending 1 }

        rearLEDCardThermalTrendingTable  OBJECT-TYPE
                SYNTAX  SEQUENCE OF RearLEDCardThermalTrendingEntry
                ACCESS  not-accessible
                STATUS  mandatory
                DESCRIPTION
                "Table of rear LED card Thermal Trending Information."
                ::= { chassisThermalTrending 10 }

        rearLEDCardThermalTrendingEntry OBJECT-TYPE
                SYNTAX RearLEDCardThermalTrendingEntry
                ACCESS  not-accessible
                STATUS  mandatory
                DESCRIPTION
                "Rear LED Card Thermal Trending entry."
                INDEX { rearLEDCardThermalTrendingIndex }
                ::= { rearLEDCardThermalTrendingTable 1 }

        RearLEDCardThermalTrendingEntry ::= SEQUENCE {
                rearLEDCardThermalTrendingIndex INTEGER,
                rearLEDCardThermalTrendingTimeStamp OCTET STRING,
                rearLEDCardThermalTrendingTemperatureAvg OCTET STRING,
                rearLEDCardThermalTrendingTemperatureMin OCTET STRING,
                rearLEDCardThermalTrendingTemperatureMax OCTET STRING
                }

        rearLEDCardThermalTrendingIndex  OBJECT-TYPE
                SYNTAX  INTEGER
                ACCESS  read-only
                STATUS  mandatory
                DESCRIPTION
                "Rear LED Card Thermal Trending Table Index."
                ::= { rearLEDCardThermalTrendingEntry 1 }

        rearLEDCardThermalTrendingTimeStamp  OBJECT-TYPE
                SYNTAX  OCTET STRING
                ACCESS  read-only
                STATUS  mandatory
                DESCRIPTION
                "Rear LED Card Thermal Trending Table Sample Timestamp."
                ::= { rearLEDCardThermalTrendingEntry 2 }

        rearLEDCardThermalTrendingTemperatureAvg  OBJECT-TYPE
                 SYNTAX  OCTET STRING
                 ACCESS  read-only
                 STATUS  mandatory
                 DESCRIPTION
                 "Rear LED Card Thermal Trending Table Average Temperature."
                 ::= { rearLEDCardThermalTrendingEntry 3 }

        rearLEDCardThermalTrendingTemperatureMin  OBJECT-TYPE
                 SYNTAX  OCTET STRING
                 ACCESS  read-only
                 STATUS  mandatory
                 DESCRIPTION
                 "Rear LED Card Thermal Trending Table Minumum Temperature."
                 ::= { rearLEDCardThermalTrendingEntry 4 }

        rearLEDCardThermalTrendingTemperatureMax  OBJECT-TYPE
                 SYNTAX  OCTET STRING
                 ACCESS  read-only
                 STATUS  mandatory
                 DESCRIPTION
                 "Rear LED Card Thermal Trending Table Maximum Temperature."
                 ::= { rearLEDCardThermalTrendingEntry 5 }


     -- ******************************************************************************
     -- Chassis Mgmt Cubic Feet per Minute Thermal Trending Table
     -- ******************************************************************************
        cfmThermalTrendingTable  OBJECT-TYPE
                SYNTAX  SEQUENCE OF CfmThermalTrendingEntry
                ACCESS  not-accessible
                STATUS  mandatory
                DESCRIPTION
                "Table of Cubic Feet per Minute Thermal Trending Information."
                ::= { chassisThermalTrending 60 }

        cfmThermalTrendingEntry OBJECT-TYPE
                SYNTAX CfmThermalTrendingEntry
                ACCESS  not-accessible
                STATUS  mandatory
                DESCRIPTION
                "Chassis CFM Thermal Trending entry."
                INDEX { cfmThermalTrendingIndex }
                ::= { cfmThermalTrendingTable 1 }

        CfmThermalTrendingEntry ::= SEQUENCE {
                cfmThermalTrendingIndex INTEGER,
                cfmThermalTrendingTimeStamp OCTET STRING,
                cfmThermalTrendingCurrentCFM OCTET STRING,
                cfmThermalTrendingMaxCFM OCTET STRING
                }

        cfmThermalTrendingIndex  OBJECT-TYPE
                SYNTAX  INTEGER
                ACCESS  read-only
                STATUS  mandatory
                DESCRIPTION
                "Cubic Feet per Minute Thermal Trending Table Index."
                ::= { cfmThermalTrendingEntry 1 }

        cfmThermalTrendingTimeStamp  OBJECT-TYPE
                SYNTAX  OCTET STRING
                ACCESS  read-only
                STATUS  mandatory
                DESCRIPTION
                "Cubic Feet per Minute Thermal Trending Table Sample Timestamp."
                ::= { cfmThermalTrendingEntry 2 }

        cfmThermalTrendingCurrentCFM  OBJECT-TYPE
                 SYNTAX  OCTET STRING
                 ACCESS  read-only
                 STATUS  mandatory
                 DESCRIPTION
                 "Cubic Feet per Minute Thermal Trending Table
                  The Current CFM of air flow calculated at this sample time."
                 ::= { cfmThermalTrendingEntry 3 }

        cfmThermalTrendingMaxCFM  OBJECT-TYPE
                 SYNTAX  OCTET STRING
                 ACCESS  read-only
                 STATUS  mandatory
                 DESCRIPTION
                 "Cubic Feet per Minute Thermal Trending Table
                  The Maximum CFM of air flow the chassis can provide
                  at this sample time."
                 ::= { cfmThermalTrendingEntry 4 }

     -- ******************************************************************************
     -- Chassis Mgmt Exhaust Heat Index Thermal Trending Table
     -- ******************************************************************************
        ehiThermalTrendingTable  OBJECT-TYPE
                SYNTAX  SEQUENCE OF EhiThermalTrendingEntry
                ACCESS  not-accessible
                STATUS  mandatory
                DESCRIPTION
                "Table of Exhaust Heat Index Thermal Trending Information."
                ::= { chassisThermalTrending 70 }

        ehiThermalTrendingEntry OBJECT-TYPE
                SYNTAX EhiThermalTrendingEntry
                ACCESS  not-accessible
                STATUS  mandatory
                DESCRIPTION
                "Chassis Exhaust Heat Index Thermal Trending entry."
                INDEX { ehiThermalTrendingIndex }
                ::= { ehiThermalTrendingTable 1 }

        EhiThermalTrendingEntry ::= SEQUENCE {
                ehiThermalTrendingIndex INTEGER,
                ehiThermalTrendingTimeStamp OCTET STRING,
                ehiThermalTrendingMinEHI OCTET STRING,
                ehiThermalTrendingMaxEHI OCTET STRING,
                ehiThermalTrendingAvgEHI OCTET STRING
                }

        ehiThermalTrendingIndex  OBJECT-TYPE
                SYNTAX  INTEGER
                ACCESS  read-only
                STATUS  mandatory
                DESCRIPTION
                "Exhaust Heat Index Thermal Trending Table Index."
                ::= { ehiThermalTrendingEntry 1 }

        ehiThermalTrendingTimeStamp  OBJECT-TYPE
                SYNTAX  OCTET STRING
                ACCESS  read-only
                STATUS  mandatory
                DESCRIPTION
                "Chassis Exhaust Heat Index Thermal Trending Table Sample Timestamp."
                ::= { ehiThermalTrendingEntry 2 }

        ehiThermalTrendingMinEHI  OBJECT-TYPE
                 SYNTAX  OCTET STRING
                 ACCESS  read-only
                 STATUS  mandatory
                 DESCRIPTION
                 "Chassis Exhaust Heat Index Thermal Trending Table
                  Minimum Exhaust Heat Index since last reboot."
                 ::= { ehiThermalTrendingEntry 3 }

        ehiThermalTrendingMaxEHI  OBJECT-TYPE
                 SYNTAX  OCTET STRING
                 ACCESS  read-only
                 STATUS  mandatory
                 DESCRIPTION
                 "Chassis Exhaust Heat Index Thermal Trending Table
                  Maximum Exhaust Heat Index since last reboot."
                 ::= { ehiThermalTrendingEntry 4 }

        ehiThermalTrendingAvgEHI  OBJECT-TYPE
                 SYNTAX  OCTET STRING
                 ACCESS  read-only
                 STATUS  mandatory
                 DESCRIPTION
                 "Chassis Exhaust Heat Index Thermal Trending Table
                  Average of last 2 Exhaust Heat Index calculations since
                  last reboot."
                 ::= { ehiThermalTrendingEntry 5 }

   -- ********************************************************************************
   -- Power Policy Table
   -- ********************************************************************************
      powerPolicyInformation  OBJECT IDENTIFIER ::= { fuelGauge 6 }

      powerPolicyTable OBJECT-TYPE
                 SYNTAX  SEQUENCE OF PowerPolicyEntry
                 ACCESS  not-accessible
                 STATUS  mandatory
                 DESCRIPTION
		 "Table of Power Policy information for all power domains. Reading this
                  table can tell you about the available power policies that can be
                  configured for a domain and also which is currently selected. The
                  powerPolicyActivate object can also be SET to select which policy
                  should be active for a given power domain."
                 ::= { powerPolicyInformation 1 }

      powerPolicyEntry OBJECT-TYPE
                 SYNTAX  PowerPolicyEntry
                 ACCESS  not-accessible
                 STATUS  mandatory
                 DESCRIPTION
                 "Power Policy Entry"
                 INDEX { powerPolicyIndex }
                 ::= { powerPolicyTable 1 }

      PowerPolicyEntry ::= SEQUENCE {
                 powerPolicyIndex INTEGER,
                 powerPolicyPowerDomainNumber INTEGER,
                 powerPolicyName OCTET STRING,
                 powerPolicyPwrSupplyFailureLimit INTEGER,
                 powerPolicyMaxPowerLimit INTEGER,
                 powerPolicyEstimatedUtilization INTEGER,
                 powerPolicyActivate INTEGER
                 }

      powerPolicyIndex  OBJECT-TYPE
                 SYNTAX  INTEGER
                 ACCESS  read-only
                 STATUS  mandatory
                 DESCRIPTION
                 "The unique idenitifier of a row in the powerPolicyTable."
                 ::= { powerPolicyEntry 1 }

      powerPolicyPowerDomainNumber  OBJECT-TYPE
                 SYNTAX  INTEGER {
                   powerDomain1(1),
                   powerDomain2(2)
                 }
                 ACCESS  read-only
                 STATUS  mandatory
                 DESCRIPTION
                 "The power domain number which this row is associated with."
                 ::= { powerPolicyEntry 2 }

      powerPolicyName  OBJECT-TYPE
                 SYNTAX  OCTET STRING
                 ACCESS  read-only
                 STATUS  mandatory
                 DESCRIPTION
  		 "The short name of the power policy. The following are the possible
                  names and their detailed description:

		  Power Module Redundancy
                        Intended for a single power source into the chassis
                        where each Power Module is on its own dedicated circuit.
                        Total allowed power draw is limited to one less than the
                        number of Power Modules when more than one Power Module is
                        present. One Power Module can fail without affecting blade
                        operation. Multiple Power Module failures can cause
                        the chassis to power off. Note that some blades may not be
                        allowed to power on if doing so would exceed the policy power
                        limit.

		  Power Module Redundancy with Blade Throttling Allowed
                        Very similar to the Power Module Redundancy policy. This
                        policy allows you to draw more total power; however, capable
                        blades may be allowed to throttle down if one Power Module fails.

		  Basic Power Management
                        Total allowed power is higher than other policies and is limited only
                        by the total power capacity of all the Power Modules up to the maximum
                        of chassis power rating. This is the least conservative approach, since
                        it does not provide any protection for power source or Power Module
                        failure. If any single power supply fails, blade and/or chassis
                        operation may be affected.

		  Power Source Redundancy
                        Intended for dual power sources into the chassis. Total
                        allowed power draw is limited to the capacity of two Power
                        Modules. This is the most conservative approach and is
                        recommended when all four Power Modules are installed.
                        When the chassis is correctly wired with dual power
                        sources, one power source can fail without affecting
                        blade operation. Note that some blades may not be
                        allowed to power on if doing so would exceed the policy
                        power limit.

		  Power Source Redundancy with Blade Throttling Allowed
                        Very similar to the Power Source Redundancy policy. This policy
                        allows you to draw more total power; however, capable blades
                        may be allowed to throttle down if one power source fails."
                 ::= { powerPolicyEntry 3 }

      powerPolicyPwrSupplyFailureLimit  OBJECT-TYPE
                 SYNTAX  INTEGER
                 ACCESS  read-only
                 STATUS  mandatory
                 DESCRIPTION
		 "The maximum number of power supplies that can fail in a chassis
                  while still providing redundancy."
                 ::= { powerPolicyEntry 4 }

      powerPolicyMaxPowerLimit  OBJECT-TYPE
                 SYNTAX  INTEGER
                 ACCESS  read-only
                 STATUS  mandatory
                 DESCRIPTION
		 "The maximum power available (in watts), based on the number of power modules and
                  the Power Management Policy setting."
                 ::= { powerPolicyEntry 5 }

      powerPolicyEstimatedUtilization  OBJECT-TYPE
                 SYNTAX  INTEGER
                 ACCESS  read-only
                 STATUS  mandatory
                 DESCRIPTION
                 "The estimated utilization (as a percentage) based on current power usage."
                 ::= { powerPolicyEntry 6 }

      powerPolicyActivate  OBJECT-TYPE
                 SYNTAX  INTEGER {
                   disabled(0),
                   enabled(1)
                 }
                 ACCESS  read-write
                 STATUS  mandatory
                 DESCRIPTION
                 "When read, this object provides the status of this power policy. If the
                  value is enabled(1), it means this is the active power policy for the
                  associated domain. When set to a value of enabled(1), the power policy
                  will be made the active one for the associated domain. A set of disabled(0)
                  is not allowed.

                  The SET may fail when the user goes from a less restrictive policy
                  to a more restrictive policy, e.g. no power management to redundant power
                  modules.

                  This happens because the MM might have allocated more power for components
                  in the less restrictive policy. Then if a user wants to go to a more restrictive
                  policy, the power available may be lower than what was already allocated.

                  The SET should always succeed if a user goes from a more restrictive to
                  a less restrictive policy."
                 ::= { powerPolicyEntry 7 }

    -- ********************************************************************************
    -- Error logs
    -- ********************************************************************************
    eventLog   OBJECT IDENTIFIER ::= { errorLogs 4 }

     -- ******************************************************************************
     -- Event Log Table - Legacy Format  
     -- ******************************************************************************
     readEventLogTable  OBJECT-TYPE
                    SYNTAX  SEQUENCE OF ReadEventLogEntry
                    ACCESS  not-accessible
                    STATUS  mandatory
                    DESCRIPTION
                    "Table of event log entry information."
                    ::= { eventLog 2 }

      readEventLogEntry OBJECT-TYPE
                    SYNTAX ReadEventLogEntry
                    ACCESS  not-accessible
                    STATUS  mandatory
                    DESCRIPTION
                    "Event log table entry"
                    INDEX { readEventLogIndex }
                    ::= { readEventLogTable 1 }

      ReadEventLogEntry ::= SEQUENCE {
                  readEventLogIndex INTEGER,
                  readEventLogString OCTET STRING
                  }

      readEventLogIndex  OBJECT-TYPE
                  SYNTAX  INTEGER
                  ACCESS  read-only
                  STATUS  mandatory
                  DESCRIPTION
                  "The event log index number."
                  ::= { readEventLogEntry 1 }

      readEventLogString OBJECT-TYPE
                  SYNTAX  OCTET STRING
                  ACCESS  read-only
                  STATUS  mandatory
                  DESCRIPTION
                  "A string of data detailing an event."
                  ::= { readEventLogEntry 2 }

     -- ******************************************************************************
     -- Event Log Configuration   
     -- ******************************************************************************
     clearEventLog OBJECT-TYPE
                  SYNTAX  INTEGER {
                    execute(1)
                  }
                  ACCESS  read-write
                  STATUS  mandatory
                  DESCRIPTION
                  "Clear the event log.

                  NOTE: Value returned for the GET command is meaningless for this
                  MIB object."
                  ::= { eventLog 3 }

     monitorLogStateEvents OBJECT-TYPE
                  SYNTAX  INTEGER {
                    disabled(0),
                    enabled(1)
                  }
                  ACCESS  read-write
                  STATUS  mandatory
                  DESCRIPTION
                  "If disabled, it means the info LED will not turn on when the log gets full
                  and no alerts will be sent out. If enabled, the LED will turn on when the log
                  gets full and alerts will be sent out."
                  ::= { eventLog 4 }

     -- ******************************************************************************
     -- Event Log Table - Enhanced Format  
     -- ******************************************************************************
       readEnhancedEventLogTable  OBJECT-TYPE
                    SYNTAX  SEQUENCE OF ReadEnhancedEventLogEntry
                    ACCESS  not-accessible
                    STATUS  mandatory
                    DESCRIPTION
                    "Table of enhanced event log entry information."
                    ::= { eventLog 6 }

      readEnhancedEventLogEntry OBJECT-TYPE
                    SYNTAX ReadEnhancedEventLogEntry
                    ACCESS  not-accessible
                    STATUS  mandatory
                    DESCRIPTION
                    "Enhaced Event log table entry, new entries could be added for new items."
                    INDEX { readEnhancedEventLogNumber }
                    ::= { readEnhancedEventLogTable 1 }

          ReadEnhancedEventLogEntry ::= SEQUENCE {
                  readEnhancedEventLogNumber Unsigned32,
                  readEnhancedEventLogAttribute OCTET STRING,
                  readEnhancedEventLogMessage OCTET STRING,
                  readEnhancedEventLogSequenceNum Unsigned32,
                  readEnhancedEventCommonEventID OCTET STRING
                  }

          readEnhancedEventLogNumber  OBJECT-TYPE
                  SYNTAX  Unsigned32(0..4294967295)
                  ACCESS  read-only
                  STATUS  mandatory
                  DESCRIPTION
                  "The event log number for the enhanced event log."
                  ::= { readEnhancedEventLogEntry 1 }

      readEnhancedEventLogAttribute OBJECT-TYPE
                  SYNTAX  OCTET STRING
                  ACCESS  read-only
                  STATUS  mandatory
                  DESCRIPTION
                  "A string of data detailing an event log's attribute, such as the
                  Event ID and Call Home Flag. The Event ID is a hexadecimal number representing an specific or class of events.
                  The call home flag indicates that the corresponding problem may result in a call home."
                  ::= { readEnhancedEventLogEntry 2}

         readEnhancedEventLogMessage OBJECT-TYPE
                  SYNTAX  OCTET STRING
                  ACCESS  read-only
                  STATUS  mandatory
                  DESCRIPTION
                  "A string of data detailing an event log message."
                  ::= { readEnhancedEventLogEntry 3}

      readEnhancedEventLogSequenceNum  OBJECT-TYPE
                  SYNTAX  Unsigned32(0..4294967295)
                  ACCESS  read-only
                  STATUS  mandatory
                  DESCRIPTION
                  "The sequence number for the enhanced event log. This number is the next
                  sequence number when this event record was create. This number continues
                  to grow, even if this event log is cleared, until it reaches the maximum
                  value of 4294967295. The next sequence number following the maximum value
                  is 1."
                  ::= { readEnhancedEventLogEntry 4 }

         readEnhancedEventCommonEventID OBJECT-TYPE
                  SYNTAX  OCTET STRING
                  ACCESS  read-only
                  STATUS  mandatory
                  DESCRIPTION
                  "A string of data detailing an enhanced event log Common Event ID."
                  ::= { readEnhancedEventLogEntry 5}

     -- ******************************************************************************
     -- Event Log Table - Enhanced Format Audit Entries 
     -- ******************************************************************************
     readAuditLogTable  OBJECT-TYPE
                    SYNTAX  SEQUENCE OF ReadAuditLogEntry
                    ACCESS  not-accessible
                    STATUS  mandatory
                    DESCRIPTION
                    "Table of audit log entry information. Audit log includes the logs whose source is 'Audit'"
                    ::= { eventLog 10 }

      readAuditLogEntry OBJECT-TYPE
                    SYNTAX ReadAuditLogEntry
                    ACCESS  not-accessible
                    STATUS  mandatory
                    DESCRIPTION
                    "Audit log table entry, new entries could be added for new items."
                    INDEX { readAuditLogNumber }
                    ::= { readAuditLogTable 1 }

      ReadAuditLogEntry ::= SEQUENCE {
                  readAuditLogNumber Unsigned32,
                  readAuditLogAttribute OCTET STRING,
                  readAuditLogMessage OCTET STRING,
                  readAuditLogSequenceNum Unsigned32,
                  readAuditLogCommonEventID OCTET STRING
                  }

      readAuditLogNumber  OBJECT-TYPE
                  SYNTAX  Unsigned32(0..4294967295)
                  ACCESS  read-only
                  STATUS  mandatory
                  DESCRIPTION
                  "The audit log number."
                  ::= { readAuditLogEntry 1 }

      readAuditLogAttribute OBJECT-TYPE
                  SYNTAX  OCTET STRING
                  ACCESS  read-only
                  STATUS  mandatory
                  DESCRIPTION
                  "A string of data detailing an audit eventlog's attribute."
                  ::= { readAuditLogEntry 2 }

      readAuditLogMessage OBJECT-TYPE
                  SYNTAX  OCTET STRING
                  ACCESS  read-only
                  STATUS  mandatory
                  DESCRIPTION
                  "A string of data detailing an audit event log message."
                  ::= { readAuditLogEntry 3 }

      readAuditLogSequenceNum  OBJECT-TYPE
                  SYNTAX  Unsigned32(0..4294967295)
                  ACCESS  read-only
                  STATUS  mandatory
                  DESCRIPTION
                  "The sequence number for the audit event log. This number is the next
                  sequence number when this event record was create. This number continues
                  to grow, even if this event log is cleared, until it reaches the maximum
                  value of 4294967295. The next sequence number following the maximum value
                  is 1."
                  ::= { readAuditLogEntry 4 }

      readAuditLogCommonEventID OBJECT-TYPE
                  SYNTAX  OCTET STRING
                  ACCESS  read-only
                  STATUS  mandatory
                  DESCRIPTION
                  "A string of data detailing an audit event log Common Event ID."
                  ::= { readAuditLogEntry 5 }

     clearAuditLog OBJECT-TYPE
                  SYNTAX  INTEGER {
                    execute(1)
                  }
                  ACCESS  read-write
                  STATUS  mandatory
                  DESCRIPTION
                  "Clear the audit log.

                  NOTE: Value returned for the GET command is meaningless for this
                  MIB object."
                  ::= { eventLog 11 }

     -- ******************************************************************************
     -- Event Log Table - Enhanced Format Non-Audit Entries 
     -- ******************************************************************************
     readSystemLogTable  OBJECT-TYPE
                    SYNTAX  SEQUENCE OF ReadSystemLogEntry
                    ACCESS  not-accessible
                    STATUS  mandatory
                    DESCRIPTION
                    "Table of system log entry information. System log includes the logs whose source is other than 'Audit'"
                    ::= { eventLog 12 }

      readSystemLogEntry OBJECT-TYPE
                    SYNTAX ReadSystemLogEntry
                    ACCESS  not-accessible
                    STATUS  mandatory
                    DESCRIPTION
                    "System log table entry, new entries could be added for new items."
                    INDEX { readSystemLogNumber }
                    ::= { readSystemLogTable 1 }

      ReadSystemLogEntry ::= SEQUENCE {
                  readSystemLogNumber Unsigned32,
                  readSystemLogAttribute OCTET STRING,
                  readSystemLogMessage OCTET STRING,
                  readSystemLogSequenceNum Unsigned32,
                  readSystemLogCommonEventID OCTET STRING
                  }

      readSystemLogNumber  OBJECT-TYPE
                  SYNTAX  Unsigned32(0..4294967295)
                  ACCESS  read-only
                  STATUS  mandatory
                  DESCRIPTION
                  "The system log index number."
                  ::= { readSystemLogEntry 1 }

      readSystemLogAttribute OBJECT-TYPE
                  SYNTAX  OCTET STRING
                  ACCESS  read-only
                  STATUS  mandatory
                  DESCRIPTION
                  "A string of data detailing an system event log's attribute."
                  ::= { readSystemLogEntry 2 }

        readSystemLogMessage OBJECT-TYPE
                  SYNTAX  OCTET STRING
                  ACCESS  read-only
                  STATUS  mandatory
                  DESCRIPTION
                  "A string of data detailing an system event log message."
                  ::= { readSystemLogEntry 3 }

      readSystemLogSequenceNum  OBJECT-TYPE
                  SYNTAX  Unsigned32(0..4294967295)
                  ACCESS  read-only
                  STATUS  mandatory
                  DESCRIPTION
                  "The sequence number for the system event log. This number is the next
                  sequence number when this event record was create. This number continues
                  to grow, even if this event log is cleared, until it reaches the maximum
                  value of 4294967295. The next sequence number following the maximum value
                  is 1."
                  ::= { readSystemLogEntry 4 }

      readSystemLogCommonEventID OBJECT-TYPE
                  SYNTAX  OCTET STRING
                  ACCESS  read-only
                  STATUS  mandatory
                  DESCRIPTION
                  "A string of data detailing an system event log Common Event ID."
                  ::= { readSystemLogEntry 5 }

     clearSystemLog OBJECT-TYPE
                  SYNTAX  INTEGER {
                    execute(1)
                  }
                  ACCESS  read-write
                  STATUS  mandatory
                  DESCRIPTION
                  "Clear the system log.

                  NOTE: Value returned for the GET command is meaningless for this
                  MIB object."
                  ::= { eventLog 13 }

     -- ******************************************************************************
     -- Event Log Table - Auxiliary Data Only
     -- ******************************************************************************
     readEventLogAuxTable  OBJECT-TYPE
                    SYNTAX  SEQUENCE OF ReadEventLogAuxEntry
                    ACCESS  not-accessible
                    STATUS  mandatory
                    DESCRIPTION
                    "Table of system log entry auxiliary information."
                    ::= { eventLog 14 }

      readEventLogAuxEntry OBJECT-TYPE
                    SYNTAX ReadEventLogAuxEntry
                    ACCESS  not-accessible
                    STATUS  mandatory
                    DESCRIPTION
                    "Event log auxiliary table entry, new entries could be added for new items."
                    INDEX { readEventLogAuxNumber }
                    ::= { readEventLogAuxTable 1 }

      ReadEventLogAuxEntry ::= SEQUENCE {
                  readEventLogAuxNumber INTEGER,
                  readEventLogAuxSequenceNum Unsigned32,
                  readEventLogAuxMessage OCTET STRING
                  }

      readEventLogAuxNumber  OBJECT-TYPE
                  SYNTAX  INTEGER
                  ACCESS  read-only
                  STATUS  mandatory
                  DESCRIPTION
                  "The system log auxiliary index number.
                  To relate this information to the system log, match Sequence number
                  of this entry to the Sequence number of the system log entry."
                  ::= { readEventLogAuxEntry 1 }

      readEventLogAuxSequenceNum  OBJECT-TYPE
                  SYNTAX  Unsigned32(0..4294967295)
                  ACCESS  read-only
                  STATUS  mandatory
                  DESCRIPTION
                  "The sequence number for the system event log that contains this Auxiliary
                  information. Value is from 1 through 4294967295 and then wraps."
                  ::= { readEventLogAuxEntry 2 }

        readEventLogAuxMessage OBJECT-TYPE
                  SYNTAX  OCTET STRING
                  ACCESS  read-only
                  STATUS  mandatory
                  DESCRIPTION
                  "A string of data detailing the auxiliary information from the log event."
                  ::= { readEventLogAuxEntry 3 }

    --  ********************************************************************************
    --  Configure the MM
    --  ********************************************************************************
    -- ********************************************************************************
    -- Remote Access Configuration
    -- ********************************************************************************
    remoteAccessConfig  OBJECT IDENTIFIER ::= { configureSP 1 }

     -- ********************************************************************************
     -- General Remote Access and Remote Alerts Configuration
     -- ********************************************************************************
     generalRemoteCfg    OBJECT IDENTIFIER ::= { remoteAccessConfig 1 }

      remoteAlertRetryDelay OBJECT-TYPE
                   SYNTAX  INTEGER {
                     oneHalfMinute(30),
                     oneMinute(60),
                     oneAndHalfMinutes(90),
                     twoMinutes(120),
                     twoAndHalfMinutes(150),
                     threeMinutes(180),
                     threeAndHalfMinutes(210),
                     fourMinutes(240)
                   }
                   ACCESS  read-write
                   STATUS  mandatory
                   DESCRIPTION
                   "Number in seconds to delay between retries if sending a
                   remote alert is unsuccessful."
                   ::= { generalRemoteCfg 3 }

      remoteAlertRetryCount OBJECT-TYPE
                   SYNTAX  INTEGER {
                     noretry(0),
                     retry1(1),
                     retry2(2),
                     retry3(3),
                     retry4(4),
                     retry5(5),
                     retry6(6),
                     retry7(7),
                     retry8(8)
                   }
                   ACCESS  read-write
                   STATUS  mandatory
                   DESCRIPTION
                   "Number of additional times a remote alert will be
                   retried if not successfully sent. A value of zero indicates
                   no retries will be attempted."
                   ::= { generalRemoteCfg 4 }

      userAuthenticationMethod OBJECT-TYPE
                    SYNTAX  INTEGER {
                       localOnly(0),
                       ldapOnly(1),
                       localFirstThenLdap(2),
                       ldapFirstThenLocal(3)
                    }
                    ACCESS  read-write
                    STATUS  mandatory
                    DESCRIPTION
                    "Use this field to specify how users attempting to login should be authenticated.
                    There are two methods:
                       Local authentication. Userid and password are verified by searching the list
                          of users locally configured under Local Login Profiles.
                       LDAP based authentication. Users are authenticated via a remote LDAP server.
                    One or both authentication methods can be selected. If both methods should be
                    used, the order must be specified."
                    ::= { generalRemoteCfg 7 }

      maxSessionsPerLDAPUser OBJECT-TYPE
                    SYNTAX INTEGER
                    ACCESS read-write
                    STATUS mandatory
                    DESCRIPTION
                    "The maximum number of simultaneous active sessions allowed for
                    each LDAP user. If the value is 0, this option is disabled. The
                    minimum value is 1 and the maximum value is 20."
                    ::= { generalRemoteCfg 9 }

      authenticationLoggingTimeout  OBJECT-TYPE
                    SYNTAX  INTEGER {
                         logAll(0),
                         fiveSeconds(1),
                         thirtySeconds(2),
                         oneMinute(3),
                         fiveMinutes(4),
                         tenMinutes(5),
                         thirtyMinutes(6),
                         oneHour(7),
                         twelveHours(8),
                         oneDay(9),
                         logNone(255)
                   }
                    ACCESS read-write
                    STATUS mandatory
                    DESCRIPTION
                    "Use this option to set how long, in seconds, MM will not log the authentication
                    events for the same user. The default setting is 5 minutes. 0 indicates log all
                    authentication events, 255 indicates don't log any new authentication events."
                   ::= { generalRemoteCfg 10 }

      trackingIP    OBJECT-TYPE
                    SYNTAX INTEGER {
                          disable(0),
                          enable(1)
                    }
                    ACCESS read-write
                    STATUS mandatory
                    DESCRIPTION
                    "This option indicates tracking different IP addresses for the same user is
                    enabled or not. If it is enabled then an access every second from
                    alternating IP addresses will result in multiple log entries,
                    regardless of the time duration set in the 'authenticaionLoggingTimeout'field.
                    If this flag is disabled, multiple accesses by varying IP addresses
                    will only be logged as 'new' accesses if they are out of the
                    'authenticationLoggingTimeout'."
                    ::= { generalRemoteCfg 11 }

    -- ********************************************************************************
    -- Account security management
    -- ********************************************************************************
     accountSecurityManagement OBJECT IDENTIFIER ::= { generalRemoteCfg 20 }

      accountSecurityLevel OBJECT-TYPE
                   SYNTAX  INTEGER {
                     legacy(0),
                     high(1),
                     custom(2)
                   }
                   ACCESS  read-write
                   STATUS  mandatory
                   DESCRIPTION
                   "The level of security needed for local user login passwords.
                        The legacy level:
                            - no password required
                            - no password expiration
                            - no password re-use restrictions
                            - no frequency of password change restrictions
                            - account is locked for 2 minutes after 5 login failures
                            - simple password rules
                            - no account inactivity monitoring
                        The high level:
                            - password required
                            - factory default 'USERID' account password must be changed on next login
                            - force user to change password on first login
                            - password expires in 90 days
                            - password re-use checking enabled (last 5 passwords kept in history)
                            - minimum 24 hours interval between password changes
                            - account is locked for 60 minutes after 5 login failures
                            - complex password rules with 2 degrees of difference from previous password
                            - alert on account inactivity after 120 days
                            - accounts disabled after 180 days of inactivity
                        The custom level:
                            - set the password settings individually under customSecuritySettings
                   The default value is legacy."
                   ::= { accountSecurityManagement 1 }

     customSecuritySettings OBJECT IDENTIFIER ::= { accountSecurityManagement 2 }


      passwordExpirationPeriod OBJECT-TYPE
                   SYNTAX  INTEGER
                   ACCESS  read-write
                   STATUS  mandatory
                   DESCRIPTION
                   "The number of days before login passwords expire.  The minimum
                   value is 1 day and the maximum value is 365 days.  The default
                   value is 90 days.  A value of 0 disables this option."
                   ::= { customSecuritySettings 2 }

      defaultAdminPasswordExpired OBJECT-TYPE
                   SYNTAX  INTEGER {
                     disabled(0),
                     enabled(1)
                   }
                   ACCESS  read-write
                   STATUS  mandatory
                   DESCRIPTION
                   "If enabled, the factory default 'USERID' account password must
                   be changed on next login.  The default value is disabled."
                   ::= { customSecuritySettings 3 }

      minimumPasswordReuseCycle OBJECT-TYPE
                   SYNTAX  INTEGER {
                     none(0),
                     onePassword(1),
                     twoPasswords(2),
                     threePasswords(3),
                     fourPasswords(4),
                     fivePasswords(5)
                   }
                   ACCESS  read-write
                   STATUS  mandatory
                   DESCRIPTION
                   "The number of unique passwords a user must choose before
                   reusing a password.  The default value is none."
                   ::= { customSecuritySettings 4 }

      complexPasswordRules OBJECT-TYPE
                   SYNTAX  INTEGER {
                     disabled(0),
                     enabled(1)
                   }
                   ACCESS  read-write
                   STATUS  mandatory
                   DESCRIPTION
                   "If enabled, the minimum complexity rules will be enforced for all
                   local login passwords and 'User login password required' rule will be enabled.

                   The complex rules are as follows:
                        must be 8-31 characters
                        must contain at least one number
                        must contain at least one letter
                        cannot contain white space characters
                        cannot be a repeat or reverse of user name
                        no more than 3 of the same characters used consecutively
                        must contain at least 2 of the following combinations:
                                at least one upper case letter
                                at least one lower case letter
                                at least one special character
                        Password and password confirm values must match

                   If disabled, the lagacy rules are:
                        must be 5-31 characters
                        must contain at least one number
                        must contain at least one letter
                        cannot contain white space characters
                        Password and password confirm values must match

                   The default value is disabled."
                   ::= { customSecuritySettings 5 }

      minimumDiffCharsPassword OBJECT-TYPE
                   SYNTAX  INTEGER {
                     none(0),
                     oneChar(1),
                     twoChars(2),
                     threeChars(3),
                     fourChars(4),
                     fiveChars(5),
                     sixChars(6),
                     sevenChars(7),
                     eightChars(8),
                     nineChars(9),
                     tenChars(10),
                     elevenChars(11),
                     twelveChars(12),
                     thirteenChars(13),
                     fourteenChars(14),
                     fifteenChars(15)
                   }
                   ACCESS  read-write
                   STATUS  mandatory
                   DESCRIPTION
                   "The required minimum number of characters in the new password
                   different from the previous password.  The default value is 2.

                   A SET of this object is ignored until the complexPasswordRules option is enabled
                   and the minimumPasswordReuseCycle is not none(0)"
                   ::= { customSecuritySettings 6 }

      changePasswordFirstAccess OBJECT-TYPE
                   SYNTAX  INTEGER {
                     disabled(0),
                     enabled(1)
                   }
                   ACCESS  read-write
                   STATUS  mandatory
                   DESCRIPTION
                   "If enabled, the login user will be forced to change their password on
                   the first access after the account has been established or on
                   the first access after an administrator has changed the password
                   for the user, except for the administrator password for USERID.
                   The default value is disabled."
                   ::= { customSecuritySettings 7 }

      inactivityAlertPeriod OBJECT-TYPE
                   SYNTAX  INTEGER
                   ACCESS  read-write
                   STATUS  mandatory
                   DESCRIPTION
                   "The period of time in days before generating an alert for a dormant
                   account. This value applies to all login accounts, including the
                   administrator account.  The minimum value is 1 day and the maximum
                   value is 365 days.  The default value is 0 which disables this option.
                   NOTE: This value must be less than the inactivityAlertDisablePeriod."
                   ::= { customSecuritySettings 8 }

      inactivityAlertDisablePeriod OBJECT-TYPE
                   SYNTAX  INTEGER
                   ACCESS  read-write
                   STATUS  mandatory
                   DESCRIPTION
                   "The period of time in days before generating an alert and disabling
                   a dormant account. This value applies to all login accounts, excluding
                   the administrator account.  The minimum value is 1 day and the maximum
                   value is 365 days.  The default value is 0 which disables this option.
                   NOTE: This value must be greater than the inactivityAlertPeriod."
                   ::= { customSecuritySettings 9 }

      lockoutPeriod OBJECT-TYPE
                   SYNTAX  INTEGER
                   ACCESS  read-write
                   STATUS  mandatory
                   DESCRIPTION
                   "The period of time in minutes that a user is locked out after the
                   maximum number of login failures was reached.  The minimum value is
                   is 1 minute and the maximum value is 2880 minutes.  The default value
                   is 2 minutes for the Legacy security level and 60 minutes for the
                   High security level.  A value of 0 disables this option."
                   ::= { customSecuritySettings 10 }

      maxLoginFailures OBJECT-TYPE
                   SYNTAX  INTEGER {
                     none(0),
                     oneTime(1),
                     twoTimes(2),
                     threeTimes(3),
                     fourTimes(4),
                     fiveTimes(5),
                     sixTimes(6),
                     sevenTimes(7),
                     eightTimes(8),
                     nineTimes(9),
                     tenTimes(10)
                   }
                   ACCESS  read-write
                   STATUS  mandatory
                   DESCRIPTION
                   "The maximum number of login failures before a user account is locked.
                   A value of 0 disables this option.  The default value is 5."
                   ::= { customSecuritySettings 11 }

      passwordChangeInterval OBJECT-TYPE
                   SYNTAX  INTEGER
                   ACCESS  read-write
                   STATUS  mandatory
                   DESCRIPTION
                   "A minimum period of time that user is not able to change
                   their own password. The range of acceptable values will be
                   from 0 to 1440 (or 60 days). A value of 0 disables this
                   option. If the password expiration period is set, it must be
                   greater than the minimum password change interval."
                   ::= { customSecuritySettings 12 }

     -- ***********************************************************************
     -- Serial Port Configuration
     -- ***********************************************************************
     serialPortCfg  OBJECT IDENTIFIER ::= { remoteAccessConfig 2 }

       portBaud     OBJECT-TYPE
                    SYNTAX  INTEGER {
                      baud2400(0),
                      baud4800(1),
                      baud9600(3),
                      baud19200(7),
                      baud38400(15),
                      baud57600(23),
                      baud115200(47)
                    }
                    ACCESS  read-write
                    STATUS  mandatory
                    DESCRIPTION
                    "Baud rate for the serial port."
                    ::= { serialPortCfg 1 }

       portParity   OBJECT-TYPE
                    SYNTAX  INTEGER {
                      none(0),
                      odd(1),
                      even(3),
                      mark(5),
                      space(7)
                    }
                    ACCESS  read-write
                    STATUS  mandatory
                    DESCRIPTION
                    "Parity setting for the serial port."
                    ::= { serialPortCfg 2 }

       portStopBits OBJECT-TYPE
                    SYNTAX  INTEGER {
                      oneStopbit(0),
                      twoOrOnePtFive(1)
                    }
                    ACCESS  read-write
                    STATUS  mandatory
                    DESCRIPTION
                    "Number of stop bits for the serial port."
                    ::= { serialPortCfg 3 }

     -- ********************************************************************************
     -- Remote Alert Profiles
     -- ********************************************************************************
     remoteAlertIds OBJECT IDENTIFIER ::= { remoteAccessConfig 3 }

      remoteAlertIdsTable   OBJECT-TYPE
                            SYNTAX  SEQUENCE OF RemoteAlertIdsEntry
                            ACCESS  not-accessible
                            STATUS  mandatory
                            DESCRIPTION
                            "Table of remote alert entries.
                            This table lets you configure remote alert recipients.
                            You can define up to 12 unique recipients.
                            NOTE: All selected alert events will be sent to all
                            enabled alert recipients."
                            ::= {  remoteAlertIds 1 }

      remoteAlertIdsEntry   OBJECT-TYPE
                            SYNTAX RemoteAlertIdsEntry
                            ACCESS  not-accessible
                            STATUS  mandatory
                            DESCRIPTION
                            "Remote alert entries."
                            INDEX { remoteAlertIdEntryIndex }
                            ::= { remoteAlertIdsTable 1 }

      RemoteAlertIdsEntry ::= SEQUENCE {
                   remoteAlertIdEntryIndex INTEGER,
                   remoteAlertIdEntryStatus INTEGER,
                   remoteAlertIdEntryIpOrHostAddress OCTET STRING,
                   remoteAlertIdEntryTextDescription OCTET STRING,
                   remoteAlertIdEntryNotificationType INTEGER,
                   remoteAlertIdEmailAddr OCTET STRING,
                   remoteAlertIdEntrySelectiveAlert INTEGER
                   }

      remoteAlertIdEntryIndex   OBJECT-TYPE
                                SYNTAX  INTEGER
                                ACCESS  read-only
                                STATUS  mandatory
                                DESCRIPTION
                                "Index for remote alert entry."
                                ::= { remoteAlertIdsEntry 1 }

      remoteAlertIdEntryStatus  OBJECT-TYPE
                                SYNTAX  INTEGER {
                                  invalid(0),
                                  disabledAndValid(1),
                                  enabledAndValid(2)
                                }
                                ACCESS  read-write
                                STATUS  mandatory
                                DESCRIPTION
                                "Remote alert entry status, invalid means entry
                                not defined yet, disabledAndValid means entry defined
                                but not enabled to send an alert, enabledAndValid means
                                entry defined and enabled to send an alert."
                                ::= { remoteAlertIdsEntry 2 }

      remoteAlertIdEntryIpOrHostAddress OBJECT-TYPE
                                SYNTAX  OCTET STRING (SIZE(0..50))
                                ACCESS  read-write
                                STATUS  mandatory
                                DESCRIPTION
                                "A null terminated string that either
                                contains an IP address of the form '1.2.3.4'
                                or a host name (if DNS is enabled) for the
                                alert entry."
                                ::= { remoteAlertIdsEntry 3 }

      remoteAlertIdEntryTextDescription  OBJECT-TYPE
                                SYNTAX  OCTET STRING (SIZE(0..50))
                                ACCESS  read-write
                                STATUS  mandatory
                                DESCRIPTION
                                "A null terminated string that contains
                                a text description of this entry."
                                ::= { remoteAlertIdsEntry 4 }

      remoteAlertIdEntryNotificationType OBJECT-TYPE
                                SYNTAX  INTEGER {
                                  unknown(0),
                                  snmpOverLan(4),
                                  emailOverLan(5)
                                }
                                ACCESS  read-write
                                STATUS  mandatory
                                DESCRIPTION
                                "Remote alert entry notification method.  Types include
                                unknown when the type can't be determined (read-only),
                                snmpOverLan for an SNMP alert over ethernet,
                                and emailOverLan for a E-Mail alert over ethernet."
                                ::= { remoteAlertIdsEntry 5 }

      remoteAlertIdEmailAddr    OBJECT-TYPE
                                SYNTAX  OCTET STRING(SIZE(0..64))
                                ACCESS  read-write
                                STATUS  mandatory
                                DESCRIPTION
                                "A null terminated string that contains an
                                E-Mail Address.  For example, 'xyz@us.lenovo.com'.
                                Used only for an E-mail over LAN notification type."
                                ::= { remoteAlertIdsEntry 9 }

      remoteAlertIdEntrySelectiveAlert OBJECT-TYPE
                                SYNTAX  INTEGER {
                                  critOnlyAlerts(0),
                                  allAlerts(1)
                                }
                                ACCESS  read-write
                                STATUS  mandatory
                                DESCRIPTION
                                "Remote alert entry selective alert setting.  A value of
                                critOnlyAlerts will only send critical alerts to this
                                remote alert recipient, a value of allAlerts will send
                                all alerts to this remote alert recipient."
                                ::= { remoteAlertIdsEntry 13 }

      generateTestAlert  OBJECT-TYPE
                   SYNTAX  INTEGER {
                    execute(1)
                   }
                   ACCESS  read-write
                   STATUS  mandatory
                   DESCRIPTION
                   "Generate a Test Alert.  This will send a test alert to all configured
                   and enabled remote alert recipients. 

                   NOTE: Value returned for the GET command is meaningless for this
                   MIB object."
                   ::= { remoteAlertIds 30 }

     -- ********************************************************************************
     -- Remote Access Profiles
     -- ********************************************************************************
     remoteAccessIds OBJECT IDENTIFIER ::= { remoteAccessConfig 4 }

     -- ********************************************************************************
     -- User Login Table
     -- ********************************************************************************
      remoteAccessIdsTable  OBJECT-TYPE
                            SYNTAX  SEQUENCE OF RemoteAccessIdsEntry
                            ACCESS  not-accessible
                            STATUS  mandatory
                            DESCRIPTION
                            "Table of remote access profiles.

                            This table lets you to configure all login profiles.

                            NOTE: By default, the management module
                            comes configured with one login profile that allows remote
                            access using a login ID of 'USERID' and a password of 'PASSW0RD'
                            (the 0 is a zero).  To avoid a potential security exposure,
                            we strongly recommend that you change this default Login
                            Profile to values of your choice."
                            ::= {  remoteAccessIds 1 }

      remoteAccessIdsEntry  OBJECT-TYPE
                            SYNTAX RemoteAccessIdsEntry
                            ACCESS  not-accessible
                            STATUS  mandatory
                            DESCRIPTION
                            "Remote access entries."
                            INDEX { remoteAccessIdEntryIndex }
                            ::= { remoteAccessIdsTable 1 }

      RemoteAccessIdsEntry ::= SEQUENCE {
                   remoteAccessIdEntryIndex INTEGER,
                   remoteAccessIdEntryUserId OCTET STRING,
                   remoteAccessIdEntryPassword OCTET STRING,
                   remoteAccessIdEntryPermgroups OCTET STRING,
                   remoteAccessIdEntryLoggedIn INTEGER,
                   remoteAccessIdEntryLastLogin OCTET STRING,
                   remoteAccessIdEntryPwdCompliant INTEGER,
                   remoteAccessIdEntryPwdExp OCTET STRING,
                   remoteAccessIdEntryDormant INTEGER,
                   remoteAccessIdEntryState INTEGER,
                   remoteAccessIdEntryAction INTEGER,
                   remoteAccessIdEntrySessionCount INTEGER,
                   remoteAccessIdEntryMaxSessions INTEGER,
                   remoteAccessIdEntryStatus EntryStatus,
                   remoteAccessIdEntryNodeIPMIProvisioned INTEGER,
                   remoteAccessIdEntryNodeSNMPv3Provisioned INTEGER
                   remoteAccessIdEntryIOModuleSNMPv3Provisioned INTEGER
            }


      remoteAccessIdEntryIndex  OBJECT-TYPE
                                SYNTAX  INTEGER(0..255)
                                ACCESS  read-only
                                STATUS  mandatory
                                DESCRIPTION
                                "Index for Remote access entry."
                                ::= { remoteAccessIdsEntry 1 }

      remoteAccessIdEntryUserId    OBJECT-TYPE
                                SYNTAX  OCTET STRING (SIZE(0..33))
                                ACCESS  read-write
                                STATUS  mandatory
                                DESCRIPTION
                                "Remote access entry null terminated string that
                                contains the userid.  It must not be a duplicate of
                                any previously configured ones. This field is only allowed to
                                be set when the entry status is under creation."
                                ::= { remoteAccessIdsEntry 2 }

      remoteAccessIdEntryPassword OBJECT-TYPE
                                SYNTAX  OCTET STRING
                                ACCESS  read-write
                                STATUS  mandatory
                                DESCRIPTION
                                "Remote access password.  The password rules are dictated 
                                by a combination of the chassis security policy setting 
                                (securityPolicySetting) and the user account security level setting 
                                (accountSecurityLevel). Refer to object complexPasswordRules to 
                                understand the requirements.

                                NOTE: Value returned by the GET command is meaningless
                                for this MIB object."
                                ::= { remoteAccessIdsEntry 3 }

      remoteAccessIdEntryPermgroups   OBJECT-TYPE
                                SYNTAX  OCTET STRING
                                ACCESS  read-write
                                STATUS  mandatory
                                DESCRIPTION
                                "A list of permission groups for this userid, delmited with a '|'"
                                ::= { remoteAccessIdsEntry 10 }

      remoteAccessIdEntryLoggedIn OBJECT-TYPE
                                SYNTAX  INTEGER {
                                    no(0),
                                    yes(1)
                                }
                                ACCESS  read-only
                                STATUS  mandatory
                                DESCRIPTION
                                "Indicates if user is currently logged in or not."
                                ::= { remoteAccessIdsEntry 11 }

      remoteAccessIdEntryLastLogin OBJECT-TYPE
                                SYNTAX  OCTET STRING
                                ACCESS  read-only
                                STATUS  mandatory
                                DESCRIPTION
                                "Timestamp for the last successful login by the user."
                                ::= { remoteAccessIdsEntry 12 }

      remoteAccessIdEntryPwdCompliant OBJECT-TYPE
                                SYNTAX  INTEGER {
                                    no(0),
                                    yes(1)
                                }
                                ACCESS  read-only
                                STATUS  mandatory
                                DESCRIPTION
                                "Indicates if user complies with all of the password
                                rules currently in effect."
                                ::= { remoteAccessIdsEntry 13 }

      remoteAccessIdEntryPwdExp OBJECT-TYPE
                                SYNTAX  OCTET STRING
                                ACCESS  read-only
                                STATUS  mandatory
                                DESCRIPTION
                                "The number of days until the user's current password expires."
                                ::= { remoteAccessIdsEntry 14 }

      remoteAccessIdEntryDormant  OBJECT-TYPE
                                SYNTAX  INTEGER {
                                    no(0),
                                    yes(1)
                                }
                                ACCESS  read-only
                                STATUS  mandatory
                                DESCRIPTION
                                "Indicates if the user account has been inactive for a
                                specified amount of time based on inactivityAlertDisablePeriod
                                in the customSecuritySettings section."
                                ::= { remoteAccessIdsEntry 15 }

      remoteAccessIdEntryState  OBJECT-TYPE
                                SYNTAX  INTEGER {
                                   disabled(0),
                                   active(1),
                                   locked(2)
                                }
                                ACCESS  read-only
                                STATUS  mandatory
                                DESCRIPTION
                                "Indicates the state of the user:
                                  Active - normal state
                                  Disabled - user cannot use account until enabled by a
                                    supervisor or chassis user account manager.  An account
                                    can get disabled after being dormant for a specified
                                    amount of time OR as a result of a supervisor or chassis
                                    user account manager disabling it.
                                  Locked - account is temporarily locked due to repeated
                                    unsuccessful login attempts as specified by lockoutPeriod
                                    in the customSecuritySettings section.  Account can be
                                    unlocked by a supervisor or chassis user account manager
                                    OR can be automatically unlocked after the lockoutPeriod expires.

                                NOTE: The disable action does not apply to supervisor or chassis
                                    user account manager accounts."
                                ::= { remoteAccessIdsEntry 16 }

      remoteAccessIdEntryAction OBJECT-TYPE
                                SYNTAX  INTEGER {
                                    disable(0),
                                    enable(1),
                                    unlock(2),
                                    notApplicable(255)
                                }
                                ACCESS  read-write
                                STATUS  mandatory
                                DESCRIPTION
                                "Actions that only a supervisor or chassis user account manager
                                can perform for each user id:
                                  Enable - enables an account in the Disabled state
                                  Disable - disables an account in the Active or Locked state
                                  Unlock - unlock an account in the Locked state

                                NOTE: The disable action does not apply to supervisor or chassis
                                    user account manager accounts.

                                NOTE: Value returned for the GET command is meaningless for this
                                    MIB object."
                                ::= { remoteAccessIdsEntry 17 }

      remoteAccessIdEntrySessionCount OBJECT-TYPE
                                      SYNTAX INTEGER
                                      ACCESS read-only
                                      STATUS mandatory
                                      DESCRIPTION
                                      "The number of sessions the user is currently logged in to."
                                      ::= { remoteAccessIdsEntry 18 }

      remoteAccessIdEntryMaxSessions OBJECT-TYPE
                                     SYNTAX INTEGER
                                     ACCESS read-write
                                     STATUS mandatory
                                     DESCRIPTION
                                     "The maximum number of simultaneous active sessions allowed for
                                     the user. If the value is 0, this option is disabled. The
                                     minimum value is 1 and the maximum value is 20."
                                     ::= { remoteAccessIdsEntry 19 }

      remoteAccessIdEntryStatus  OBJECT-TYPE
                            SYNTAX      EntryStatus
                            ACCESS      read-write
                            STATUS      mandatory
                            DESCRIPTION
                            "This object manages the creation and deletion of this entry.
                            The steps recommended to add a new group are:
                                1. Create a new entry in this table
                                   remoteAccessIdEntryStatus = createRequest
                                2. Set remoteAccessId as required.
                                   The remoteAccessIdUserId and the remoteAccessIdPassword must be set
                                   before the entry becomes valid.  To set the remoteAccessIdsEntryPermgroups or
                                   remoteAccessIdsEntryMaxSessions before the entry is valid, set these fields before
                                   both the password and userId are set. 
                             Only one row will be allowed to be underCreation at one time, and it must have the next index
                             in the table.
                                 
                            valid(1)         - Indicates that the group represented
                                               by this entry is available for use.

                            createRequest(2) - A new entry will be created in this table
                                               for the specified group and the new entry
                                               will transition to the underCreation(3).

                            underCreation(3) - Indicates that this entry exists in the
                                               agent but is unavailable for use. After completing the
                                               create operation, the agent will set this object to
                                               underCreation(3).

                            invalid(4)       - Deletes this entry."
                            ::= { remoteAccessIdsEntry 20 }

      remoteAccessIdEntryNodeIPMIProvisioned OBJECT-TYPE
                                SYNTAX  INTEGER {
                                    no(0),
                                    yes(1)
                                }
                                ACCESS  read-write
                                STATUS  mandatory
                                DESCRIPTION
                                "Indicates if the user has been provisioned as an IPMI account for nodes.

                                If this user is provisioned as an IPMI account, the nodes (scope) and authorities will
                                be determined by the scope and authorities of the permission groups to which this user belongs.  These can be
                                seen in the remoteAccessRBSscopeTable and remoteAccessRBSroleTable for the permission groups to which this user
                                is assigned.

                                If the userid is longer than 16 characters or there are more than 12 user accounts enabled for IPMI provisioning,
                                setting the value to yes will return an error. 

                                When provisioning an IPMI account by setting this object to yes(1), the SNMPv3 account is also automatically
                                provisioned."
                                ::= { remoteAccessIdsEntry 21 }

      remoteAccessIdEntryNodeSNMPv3Provisioned OBJECT-TYPE
                                SYNTAX  INTEGER {
                                    no(0),
                                    yes(1)
                                }
                                ACCESS  read-write
                                STATUS  mandatory
                                DESCRIPTION
                                "Indicates if the user has been provisioned as an SNMPv3 account for nodes.

                                If this user is provisioned as an SNMPv3 account, the nodes (scope) and authorities will
                                be determined by the scope and authorities of the permission groups to which this user belongs.  These can be
                                seen in the remoteAccessRBSscopeTable and remoteAccessRBSroleTable for the permission groups to which this user
                                is assigned.

                                If the userid is longer than 16 characters or there are more than 12 user accounts enabled for SNMPv3 provisioning,
                                setting the value to yes will return an error. 

                                When provisioning a SNMPv3 account by setting this object to yes(1), the IPMI account is also automatically
                                provisioned."
                                ::= { remoteAccessIdsEntry 22 }


      remoteAccessIdEntryIOModuleSNMPv3Provisioned OBJECT-TYPE
                                SYNTAX  INTEGER {
                                    no(0),
                                    yes(1)
                                }
                                ACCESS  read-write
                                STATUS  mandatory
                                DESCRIPTION
                                "Indicates if the user has been provisioned as an SNMPv3 account for I/O Modules.

                                If this is user is provisioned as an SNMPv3 account, the I/O Modules (scope) and authorities will
                                be determined by the scope and authorities of the permission groups to which this user belongs.  These can be
                                seen in the remoteAccessRBSscopeTable and remoteAccessRBSroleTable for the permission groups to which this user
                                is assigned.

                                If the userid is longer than 16 characters or there are more than 12 user accounts enabled for SNMPv3 provisioning,
                                setting the value to yes will return an error."
                                ::= { remoteAccessIdsEntry 23 }


     -- ********************************************************************************
     -- User Login Role Table
     -- ********************************************************************************
      remoteAccessRBSroleTable  OBJECT-TYPE
                    SYNTAX  SEQUENCE OF RemoteAccessRBSroleEntry
                    ACCESS  not-accessible
                    STATUS  mandatory
                    DESCRIPTION
                    "Table of RBS User Role profiles."
                    ::= {  remoteAccessIds 3 }

      remoteAccessRBSroleEntry  OBJECT-TYPE
                    SYNTAX RemoteAccessRBSroleEntry
                    ACCESS  not-accessible
                    STATUS  mandatory
                    DESCRIPTION
                    "User Role entries."
                    INDEX { roleIndex }
                    ::= { remoteAccessRBSroleTable 1 }

      RemoteAccessRBSroleEntry ::= SEQUENCE {
                    roleIndex INTEGER,
                    roleId OCTET STRING,
                    rbsSupervisor INTEGER,
                    rbsOperator INTEGER,
                    rbsChassisOperator INTEGER,
                    rbsChassisAccountManagement INTEGER,
                    rbsChassisLogManagement INTEGER,
                    rbsChassisConfiguration INTEGER,
                    rbsChassisAdministration INTEGER,
                    rbsBladeOperator INTEGER,
                    rbsBladeRemotePresence INTEGER,
                    rbsBladeConfiguration INTEGER,
                    rbsBladeAdministration INTEGER,
                    rbsSwitchModuleOperator INTEGER,
                    rbsSwitchModuleConfiguration INTEGER,
                    rbsSwitchModuleAdministration INTEGER,
                    rbsEntryStatus EntryStatus
                    }


      roleIndex  OBJECT-TYPE
                    SYNTAX  INTEGER(0..255)
                    ACCESS  read-only
                    STATUS  mandatory
                    DESCRIPTION
                    "Index for RBS User Role entry."
                    ::= { remoteAccessRBSroleEntry 1 }

      roleId    OBJECT-TYPE
                    SYNTAX  OCTET STRING (SIZE(0..63))
                    ACCESS  read-write
                    STATUS  mandatory
                    DESCRIPTION
                    "Remote access RBS role entry null terminated string that
                    contains the permission group ID.  It must not be a duplicate of
                    any previously configured ones. This field is only allowed to
                    be set when the entry status is under creation."
                    ::= { remoteAccessRBSroleEntry 2 }

      rbsSupervisor OBJECT-TYPE
                    SYNTAX  INTEGER {
                       disabled(0),
                       enabled(1)
                    }
                    ACCESS  read-write
                    STATUS  mandatory
                    DESCRIPTION
                    "User has no restrictions."
                    ::= { remoteAccessRBSroleEntry 3 }

      rbsOperator OBJECT-TYPE
                    SYNTAX  INTEGER {
                       disabled(0),
                       enabled(1)
                    }
                    ACCESS  read-write
                    STATUS  mandatory
                    DESCRIPTION
                    "User has read-only access, and cannot perform
                    any save, modify, clear, or state affecting operations
                    (e.g. restart MM, restore defaults, upgrade the firmware, etc.)."
                    ::= { remoteAccessRBSroleEntry 4 }

      rbsChassisOperator OBJECT-TYPE
                    SYNTAX  INTEGER {
                       disabled(0),
                       enabled(1)
                    }
                    ACCESS  read-write
                    STATUS  mandatory
                    DESCRIPTION
                    "User has ability to browse status and properties of
                    chassis components (MM, chassis fans, midplane, power modules).
                    Ability to backup MM configuration to a file.
                    Saving MM configuration to chassis requires supervisor access."
                    ::= { remoteAccessRBSroleEntry 5 }

      rbsChassisAccountManagement OBJECT-TYPE
                    SYNTAX  INTEGER {
                       disabled(0),
                       enabled(1)
                    }
                    ACCESS  read-write
                    STATUS  mandatory
                    DESCRIPTION
                    "User can add/modify/delete user login profiles. Ability
                    to backup MM configuration to a file. Changing global login
                    settings require chassis configuration authority."
                    ::= { remoteAccessRBSroleEntry 6 }

      rbsChassisLogManagement OBJECT-TYPE
                    SYNTAX  INTEGER {
                       disabled(0),
                       enabled(1)
                    }
                    ACCESS  read-write
                    STATUS  mandatory
                    DESCRIPTION
                    "User has ability to clear the MM event log, change log
                    policy settings, and backup MM configuration to a file."
                    ::= { remoteAccessRBSroleEntry 7 }

      rbsChassisConfiguration OBJECT-TYPE
                    SYNTAX  INTEGER {
                       disabled(0),
                       enabled(1)
                    }
                    ACCESS  read-write
                    STATUS  mandatory
                    DESCRIPTION
                    "User can modify and save any chassis configuration
                    parameter (except user profiles and event log settings).
                    Ability to restore MM factory defaults if the user also has
                    chassis administration permissions. Ability to change the
                    global login settings, SOL configuration, and backup MM
                    configuration to a file."
                    ::= { remoteAccessRBSroleEntry 8 }

      rbsChassisAdministration OBJECT-TYPE
                    SYNTAX  INTEGER {
                       disabled(0),
                       enabled(1)
                    }
                    ACCESS  read-write
                    STATUS  mandatory
                    DESCRIPTION
                    "User has ability to do MM firmware updates, modify chassis
                    LEDs, restore MM factory defaults if the user also has
                    chassis configuration permissions. Ability to restart MM
                    and backup MM configuration to a file."
                    ::= { remoteAccessRBSroleEntry 9 }

      rbsBladeOperator OBJECT-TYPE
                    SYNTAX  INTEGER {
                       disabled(0),
                       enabled(1)
                    }
                    ACCESS  read-write
                    STATUS  mandatory
                    DESCRIPTION
                    "User has ability to browse status and properties of
                    blades."
                    ::= { remoteAccessRBSroleEntry 10 }

      rbsBladeRemotePresence OBJECT-TYPE
                    SYNTAX  INTEGER {
                       disabled(0),
                       enabled(1)
                    }
                    ACCESS  read-write
                    STATUS  mandatory
                    DESCRIPTION
                    "User has ability to access the blades remote console.
                    The ability to issue the CLI
                    console command to start an SOL session to a blade will
                    also require this authority."
                    ::= { remoteAccessRBSroleEntry 11 }

      rbsBladeConfiguration OBJECT-TYPE
                    SYNTAX  INTEGER {
                       disabled(0),
                       enabled(1)
                    }
                    ACCESS  read-write
                    STATUS  mandatory
                    DESCRIPTION
                    "User can modify and save any blade configuration parameter."
                    ::= { remoteAccessRBSroleEntry 12 }

      rbsBladeAdministration OBJECT-TYPE
                    SYNTAX  INTEGER {
                       disabled(0),
                       enabled(1)
                    }
                    ACCESS  read-write
                    STATUS  mandatory
                    DESCRIPTION
                    "User can power on/off and restart blades, activate
                    standby blades, do firmware updates, and modify blade LEDs."
                    ::= { remoteAccessRBSroleEntry 13 }

      rbsSwitchModuleOperator OBJECT-TYPE
                    SYNTAX  INTEGER {
                       disabled(0),
                       enabled(1)
                    }
                    ACCESS  read-write
                    STATUS  mandatory
                    DESCRIPTION
                    "User has ability to browse status and properties of
                    I/O Modules, and to ping I/O Modules."
                    ::= { remoteAccessRBSroleEntry 14 }

      rbsSwitchModuleConfiguration OBJECT-TYPE
                    SYNTAX  INTEGER {
                       disabled(0),
                       enabled(1)
                    }
                    ACCESS  read-write
                    STATUS  mandatory
                    DESCRIPTION
                    "User can modify the I/O Module IP address, configure
                    I/O Module Advanced Management parameters, and restore
                    factory defaults on an I/O Module. Note that a user
                    requires both I/O Module configuration and I/O Module
                    administration roles in order to be able to launch a telnet
                    or web UI session to an I/O Module, or to restore factory
                    defaults on an I/O Module."
                    ::= { remoteAccessRBSroleEntry 15 }

      rbsSwitchModuleAdministration OBJECT-TYPE
                    SYNTAX  INTEGER {
                       disabled(0),
                       enabled(1)
                    }
                    ACCESS  read-write
                    STATUS  mandatory
                    DESCRIPTION
                    "User can power on/off and restart the I/O Modules,
                    update I/O Module firmware, enable/disable the Fast POST
                    and External Ports of an I/O Module. Note that a user
                    requires both I/O Module configuration and I/O Module
                    administration roles in order to be able to launch a telnet
                    session to an I/O Module, or to restore factory
                    defaults on an I/O Module."
                    ::= { remoteAccessRBSroleEntry 16 }

       rbsEntryStatus       OBJECT-TYPE
                            SYNTAX      EntryStatus
                            ACCESS      read-write
                            STATUS      mandatory
                            DESCRIPTION
                            "This object manages the creation and deletion of this entry.
                            The steps recommended to add a new group are:
                                1. Create a new entry in this table
                                   rbsEntryStatus = createRequest
                                2. Set roleId as required.
                             Only one row will be allowed to be underCreation at one time, and it must have the next index
                             in the table.

                            valid(1)         - Indicates that the group represented
                                               by this entry is available for use.

                            createRequest(2) - A new entry will be created in this table
                                               for the specified group and the new entry
                                               will transition to the underCreation(3).

                            underCreation(3) - Indicates that this entry exists in the
                                               agent but is unavailable for use. After completing the
                                               create operation, the agent will set this object to
                                               underCreation(3).

                            invalid(4)       - Deletes this entry."
                            ::= { remoteAccessRBSroleEntry 23 }

     -- ********************************************************************************
     -- User Login Scope Table
     -- ********************************************************************************
      remoteAccessRBSscopeTable  OBJECT-TYPE
                    SYNTAX  SEQUENCE OF RemoteAccessRBSscopeEntry
                    ACCESS  not-accessible
                    STATUS  mandatory
                    DESCRIPTION
                    "Table of RBS User Scope profiles."
                    ::= {  remoteAccessIds 4 }

      remoteAccessRBSscopeEntry  OBJECT-TYPE
                    SYNTAX RemoteAccessRBSscopeEntry
                    ACCESS  not-accessible
                    STATUS  mandatory
                    DESCRIPTION
                    "User Scope entries."
                    INDEX { scopeIndex }
                    ::= { remoteAccessRBSscopeTable 1 }

      RemoteAccessRBSscopeEntry ::= SEQUENCE {
                    scopeIndex INTEGER,
                    scopeId OCTET STRING,
                    rbsChassis INTEGER,
                    rbsBlade1 INTEGER,
                    rbsBlade2 INTEGER,
                    rbsBlade3 INTEGER,
                    rbsBlade4 INTEGER,
                    rbsBlade5 INTEGER,
                    rbsBlade6 INTEGER,
                    rbsBlade7 INTEGER,
                    rbsBlade8 INTEGER,
                    rbsBlade9 INTEGER,
                    rbsBlade10 INTEGER,
                    rbsBlade11 INTEGER,
                    rbsBlade12 INTEGER,
                    rbsBlade13 INTEGER,
                    rbsBlade14 INTEGER,
                    rbsSwitch1 INTEGER,
                    rbsSwitch2 INTEGER,
                    rbsSwitch3 INTEGER,
                    rbsSwitch4 INTEGER,
                    rbsSwitch5 INTEGER,
                    rbsSwitch6 INTEGER,
                    rbsSwitch7 INTEGER,
                    rbsSwitch8 INTEGER,
                    rbsSwitch9 INTEGER,
                    rbsSwitch10 INTEGER
                    }

      scopeIndex    OBJECT-TYPE
                    SYNTAX  INTEGER(0..255)
                    ACCESS  read-only
                    STATUS  mandatory
                    DESCRIPTION
                    "Index for RBS User Scope Entry."
                    ::= { remoteAccessRBSscopeEntry 1 }

      scopeId       OBJECT-TYPE
                    SYNTAX  OCTET STRING (SIZE(0..63))
                    ACCESS  read-only
                    STATUS  mandatory
                    DESCRIPTION
                    "Remote access RBS scope entry null terminated string that
                    contains the permission group ID."
                    ::= { remoteAccessRBSscopeEntry 2 }

      rbsChassis    OBJECT-TYPE
                    SYNTAX  INTEGER {
                       disabled(0),
                       enabled(1)
                    }
                    ACCESS  read-write
                    STATUS  mandatory
                    DESCRIPTION
                    "User has access to the MM and chassis functions."
                    ::= { remoteAccessRBSscopeEntry 3 }

      rbsBlade1     OBJECT-TYPE
                    SYNTAX  INTEGER {
                       disabled(0),
                       enabled(1)
                    }
                    ACCESS  read-write
                    STATUS  mandatory
                    DESCRIPTION
                    "User has access to the blade in slot 1."
                    ::= { remoteAccessRBSscopeEntry 4 }

      rbsBlade2     OBJECT-TYPE
                    SYNTAX  INTEGER {
                       disabled(0),
                       enabled(1)
                    }
                    ACCESS  read-write
                    STATUS  mandatory
                    DESCRIPTION
                    "User has access to the blade in slot 2."
                    ::= { remoteAccessRBSscopeEntry 5 }

      rbsBlade3     OBJECT-TYPE
                    SYNTAX  INTEGER {
                       disabled(0),
                       enabled(1)
                    }
                    ACCESS  read-write
                    STATUS  mandatory
                    DESCRIPTION
                    "User has access to the blade in slot 3."
                    ::= { remoteAccessRBSscopeEntry 6 }

      rbsBlade4     OBJECT-TYPE
                    SYNTAX  INTEGER {
                       disabled(0),
                       enabled(1)
                    }
                    ACCESS  read-write
                    STATUS  mandatory
                    DESCRIPTION
                    "User has access to the blade in slot 4."
                    ::= { remoteAccessRBSscopeEntry 7 }

      rbsBlade5     OBJECT-TYPE
                    SYNTAX  INTEGER {
                       disabled(0),
                       enabled(1)
                    }
                    ACCESS  read-write
                    STATUS  mandatory
                    DESCRIPTION
                    "User has access to the blade in slot 5."
                    ::= { remoteAccessRBSscopeEntry 8 }

      rbsBlade6     OBJECT-TYPE
                    SYNTAX  INTEGER {
                       disabled(0),
                       enabled(1)
                    }
                    ACCESS  read-write
                    STATUS  mandatory
                    DESCRIPTION
                    "User has access to the blade in slot 6."
                    ::= { remoteAccessRBSscopeEntry 9 }

      rbsBlade7     OBJECT-TYPE
                    SYNTAX  INTEGER {
                       disabled(0),
                       enabled(1)
                    }
                    ACCESS  read-write
                    STATUS  mandatory
                    DESCRIPTION
                    "User has access to the blade in slot 7."
                    ::= { remoteAccessRBSscopeEntry 10 }

      rbsBlade8     OBJECT-TYPE
                    SYNTAX  INTEGER {
                       disabled(0),
                       enabled(1)
                    }
                    ACCESS  read-write
                    STATUS  mandatory
                    DESCRIPTION
                    "User has access to the blade in slot 8."
                    ::= { remoteAccessRBSscopeEntry 11 }

      rbsBlade9     OBJECT-TYPE
                    SYNTAX  INTEGER {
                       disabled(0),
                       enabled(1)
                    }
                    ACCESS  read-write
                    STATUS  mandatory
                    DESCRIPTION
                    "User has access to the blade in slot 9."
                    ::= { remoteAccessRBSscopeEntry 12 }

      rbsBlade10    OBJECT-TYPE
                    SYNTAX  INTEGER {
                       disabled(0),
                       enabled(1)
                    }
                    ACCESS  read-write
                    STATUS  mandatory
                    DESCRIPTION
                    "User has access to the blade in slot 10."
                    ::= { remoteAccessRBSscopeEntry 13 }

      rbsBlade11    OBJECT-TYPE
                    SYNTAX  INTEGER {
                       disabled(0),
                       enabled(1)
                    }
                    ACCESS  read-write
                    STATUS  mandatory
                    DESCRIPTION
                    "User has access to the blade in slot 11."
                    ::= { remoteAccessRBSscopeEntry 14 }

      rbsBlade12    OBJECT-TYPE
                    SYNTAX  INTEGER {
                       disabled(0),
                       enabled(1)
                    }
                    ACCESS  read-write
                    STATUS  mandatory
                    DESCRIPTION
                    "User has access to the blade in slot 12."
                    ::= { remoteAccessRBSscopeEntry 15 }

      rbsBlade13    OBJECT-TYPE
                    SYNTAX  INTEGER {
                       disabled(0),
                       enabled(1)
                    }
                    ACCESS  read-write
                    STATUS  mandatory
                    DESCRIPTION
                    "User has access to the blade in slot 13."
                    ::= { remoteAccessRBSscopeEntry 16 }

      rbsBlade14    OBJECT-TYPE
                    SYNTAX  INTEGER {
                       disabled(0),
                       enabled(1)
                    }
                    ACCESS  read-write
                    STATUS  mandatory
                    DESCRIPTION
                    "User has access to the blade in slot 14."
                    ::= { remoteAccessRBSscopeEntry 17 }

      rbsSwitch1    OBJECT-TYPE
                    SYNTAX  INTEGER {
                       disabled(0),
                       enabled(1)
                    }
                    ACCESS  read-write
                    STATUS  mandatory
                    DESCRIPTION
                    "User has access to I/O module 1."
                    ::= { remoteAccessRBSscopeEntry 18 }

      rbsSwitch2    OBJECT-TYPE
                    SYNTAX  INTEGER {
                       disabled(0),
                       enabled(1)
                    }
                    ACCESS  read-write
                    STATUS  mandatory
                    DESCRIPTION
                    "User has access to I/O module 2."
                    ::= { remoteAccessRBSscopeEntry 19 }

      rbsSwitch3    OBJECT-TYPE
                    SYNTAX  INTEGER {
                       disabled(0),
                       enabled(1)
                    }
                    ACCESS  read-write
                    STATUS  mandatory
                    DESCRIPTION
                    "User has access to I/O module 3."
                    ::= { remoteAccessRBSscopeEntry 20 }

      rbsSwitch4    OBJECT-TYPE
                    SYNTAX  INTEGER {
                       disabled(0),
                       enabled(1)
                    }
                    ACCESS  read-write
                    STATUS  mandatory
                    DESCRIPTION
                    "User has access to I/O module 4."
                    ::= { remoteAccessRBSscopeEntry 21 }

      rbsSwitch5    OBJECT-TYPE
                    SYNTAX  INTEGER {
                       disabled(0),
                       enabled(1)
                    }
                    ACCESS  read-write
                    STATUS  mandatory
                    DESCRIPTION
                    "User has access to I/O module 5."
                    ::= { remoteAccessRBSscopeEntry 22 }

      rbsSwitch6    OBJECT-TYPE
                    SYNTAX  INTEGER {
                       disabled(0),
                       enabled(1)
                    }
                    ACCESS  read-write
                    STATUS  mandatory
                    DESCRIPTION
                    "User has access to I/O module 6."
                    ::= { remoteAccessRBSscopeEntry 23 }

      rbsSwitch7    OBJECT-TYPE
                    SYNTAX  INTEGER {
                       disabled(0),
                       enabled(1)
                    }
                    ACCESS  read-write
                    STATUS  mandatory
                    DESCRIPTION
                    "User has access to I/O module 7."
                    ::= { remoteAccessRBSscopeEntry 24 }

      rbsSwitch8    OBJECT-TYPE
                    SYNTAX  INTEGER {
                       disabled(0),
                       enabled(1)
                    }
                    ACCESS  read-write
                    STATUS  mandatory
                    DESCRIPTION
                    "User has access to I/O module 8."
                    ::= { remoteAccessRBSscopeEntry 25 }

      rbsSwitch9    OBJECT-TYPE
                    SYNTAX  INTEGER {
                       disabled(0),
                       enabled(1)
                    }
                    ACCESS  read-write
                    STATUS  mandatory
                    DESCRIPTION
                    "User has access to I/O module 9."
                    ::= { remoteAccessRBSscopeEntry 26 }

      rbsSwitch10   OBJECT-TYPE
                    SYNTAX  INTEGER {
                       disabled(0),
                       enabled(1)
                    }
                    ACCESS  read-write
                    STATUS  mandatory
                    DESCRIPTION
                    "User has access to I/O module 10."
                    ::= { remoteAccessRBSscopeEntry 27 }

      cmmNodeCentralManagerIPMISNMPv3   OBJECT-TYPE
                    SYNTAX  INTEGER {
                       disabled(0),
                       enabled(1)
                    }
                    ACCESS  read-write
                    STATUS  mandatory
                    DESCRIPTION
                    "Indicates whether CMM is the central manager of the IPMI and SNMPv3 accounts for nodes.
                    Once the CMM state is enabled, it can be cleared by seting this object to disabled.
                    WARNING: Enabling CMM IPMI/SNMPv3 user account management will cause all presently
                    existing IPMI/SNMPv3 user accounts on nodes to be overwritten.  Please be
                    sure to save any existing node IPMI/SNMPv3 account information before proceeding."
                    ::= { remoteAccessIds 9 }

      cmmIOModuleCentralManagerSNMPv3   OBJECT-TYPE
                    SYNTAX  INTEGER {
                       disabled(0),
                       enabled(1)
                    }
                    ACCESS  read-write
                    STATUS  mandatory
                    DESCRIPTION
                    "Indicates whether CMM is the central manager of the SNMPv3 accounts for I/O Modules.
                    Once the CMM state is enabled, it can be cleared by setting this object to disabled.
                    WARNING: Enabling CMM SNMPv3 user account management will disable all presently
                    existing SNMPv3 user accounts on the I/O Modules which have SIOM enabled."
                    ::= { remoteAccessIds 10 }


    -- ********************************************************************************
    -- Enable/Disable User Interfaces
    -- ********************************************************************************
    userInterfaces OBJECT IDENTIFIER ::= { remoteAccessConfig 5 }
      cli           OBJECT-TYPE
                    SYNTAX  INTEGER {
                       disabled(0),
                       telnet-only(1),
                       ssh-only(2),
                       enabled(3)
                    }
                    ACCESS  read-write
                    STATUS  mandatory
                    DESCRIPTION
                    "Enable/Disable CLI access to the MM (telnet and SSH).
                    The value enabled(3) means both telnet and ssh are enabled."
                    ::= { userInterfaces 1 }

      snmp          OBJECT-TYPE
                    SYNTAX  INTEGER {
                       disabled(0),
                       v1-only(1),
                       v3-only(2),
                       enabled(3)
                    }
                    ACCESS  read-write
                    STATUS  mandatory
                    DESCRIPTION
                    "Enable/Disable SNMP v1 and v3 access to the MM.
                    The value enabled(3) means both telnet and ssh are enabled."
                    ::= { userInterfaces 2 }

      tcm           OBJECT-TYPE
                    SYNTAX  INTEGER (0..20)
                    ACCESS  read-write
                    STATUS  mandatory
                    DESCRIPTION
                    "Enable/Disable TCP command mode (TCM) access to the MM.
                     A value of 0 means disabled, any value from 1 to 20 means enabled.

                     NOTE: MM will provide a max of 20 connections for both
                     Secure TCP Command Mode and TCP Command Mode."
                    ::= { userInterfaces 3 }

      web           OBJECT-TYPE
                    SYNTAX  INTEGER {
                       disabled(0),
                       enabled(1)
                    }
                    ACCESS  read-write
                    STATUS  mandatory
                    DESCRIPTION
                    "Enable/Disable Web access (HTTP/HTTPS) to the MM.

                     NOTE: Disabling web access to the MM will cause all
                           currently active web sessions to disconnect,
                           and you will no longer be able to access the
                           MM management functions using a web browser."
                    ::= { userInterfaces 4 }

      stcm           OBJECT-TYPE
                    SYNTAX  INTEGER (0..20)
                    ACCESS  read-write
                    STATUS  mandatory
                    DESCRIPTION
                    "Enable/Disable secure TCP command mode (STCM) access to the MM.
                     A value of 0 means disabled, any value from 1 to 20 means enabled.
                     NOTE: MM will provide a max of 20 connections for both
                           Secure TCP Command Mode and TCP Command Mode.
                           If no valid server certificate is in place,
                           Secure TCP Command Mode will not be allowed to set to enable."
                    ::= { userInterfaces 5 }

     -- ********************************************************************************
     -- User Login SSH Client Authentication Public Key Group
     -- ********************************************************************************
    mmSshClientAuth OBJECT IDENTIFIER ::= { remoteAccessConfig 6 }

    mmSshClientAuthPubKeyTable OBJECT-TYPE
        SYNTAX      SEQUENCE OF MmSshClientAuthPubKeyEntry
        ACCESS      not-accessible
        STATUS      mandatory
        DESCRIPTION
        "A table that contains client authentication
        public key information."
        ::= { mmSshClientAuth 1 }

    mmSshClientAuthPubKeyEntry OBJECT-TYPE
        SYNTAX      MmSshClientAuthPubKeyEntry
        ACCESS      not-accessible
        STATUS      mandatory
        DESCRIPTION
        "A information list about a particular SSH
        public key used for client authentication.
        The primary table index is the same value as
        the associated remoteAccessIdEntryIndex.
        The secondary table index allows selection
        of the Nth public key for that
        remoteAccessIdEntryIndex."
        INDEX { mmSshClientAuthRemoteAccessIdIndex ,
                mmSshClientAuthPubKeyIndex }
        ::= { mmSshClientAuthPubKeyTable 1 }

    MmSshClientAuthPubKeyEntry ::=
        SEQUENCE {
            mmSshClientAuthRemoteAccessIdIndex      INTEGER,
            mmSshClientAuthPubKeyIndex              INTEGER,
            mmSshClientAuthPubKeyType               INTEGER,
            mmSshClientAuthPubKeySize               INTEGER,
            mmSshClientAuthPubKeyFingerprint        OCTET STRING,
            mmSshClientAuthPubKeyAcceptFrom         OCTET STRING,
            mmSshClientAuthPubKeyComment            OCTET STRING,
            mmSshClientAuthPubKeyAction             INTEGER,
            mmSshClientAuthPubKeyEntryStatus        EntryStatus,
            mmSshClientAuthPubKeyUserId             OCTET STRING
      }

    mmSshClientAuthRemoteAccessIdIndex  OBJECT-TYPE
        SYNTAX      INTEGER
        ACCESS      read-only
        STATUS      mandatory
        DESCRIPTION
        "The primary table index is the same value as
        the associated remoteAccessIdEntryIndex used
        as an index into the remoteAccessIdsTable."
        ::= { mmSshClientAuthPubKeyEntry 1 }

    mmSshClientAuthPubKeyIndex  OBJECT-TYPE
        SYNTAX  INTEGER
        ACCESS  read-only
        STATUS  mandatory
        DESCRIPTION
        "The secondary table index used to select
         one of the client authentication public
         keys for a particular remote access Id.
         The index is an integer value from 1 to N
         where N is the number of keys associated
         with a particular remote access Id.
         An addition always causes the value of N to increase
         by one, effectively adding an entry after the
         existing keys for that remote access Id.
         If an entry is deleted from the table by
         setting mmSshClientAuthPubKeyEntryStatus = invalid,
         the key associated with that entry is deleted.
         If the deleted key was not the last key for
         a remote access Id (mmSshClientAuthPubKeyIndex is
         not the 'last' or Nth entry), the subsequent entries
         are renumbered after the deletion. A deletion
         always causes the value of N to decrease by one.
         The underlying SSH server implementation searches
         the keys in order from 1 to N when attempting public
         key authentication.

         NOTE:A maximum of 4 public keys can be installed
         for one remote access Id. "
        ::= { mmSshClientAuthPubKeyEntry 2 }

    mmSshClientAuthPubKeyType     OBJECT-TYPE
        SYNTAX  INTEGER {
            sshDss   (1),
            sshRsa   (2)
        }
        ACCESS        read-only
        STATUS        mandatory
        DESCRIPTION
        "The type of the SSH public key represented by
         this entry."
        ::= { mmSshClientAuthPubKeyEntry 3 }

    mmSshClientAuthPubKeySize          OBJECT-TYPE
        SYNTAX  INTEGER {
            bits512   (1),
            bits768   (2),
            bits1024  (3),
            bits2048  (4),
            bits4096  (5)
        }
        ACCESS        read-only
        STATUS        mandatory
        DESCRIPTION
        "The size of the SSH public key represented by
        this entry."
        ::= { mmSshClientAuthPubKeyEntry 4 }

    mmSshClientAuthPubKeyFingerprint   OBJECT-TYPE
        SYNTAX        OCTET STRING
        ACCESS        read-only
        STATUS        mandatory
        DESCRIPTION
        "The RSA fingerprint of the SSH public key represented
        by this entry.
        This value can be used with the SSH client to
        verify, on the initial connection, that the Secure Shell
        server responding to the request is the server running
        on the managed entity.  This is the fingerprint of the
        operational host key pair.  If the key pair represented
        by this entry is not operational then sixteen null octets
        must be returned."
        ::= { mmSshClientAuthPubKeyEntry 5 }

    mmSshClientAuthPubKeyAcceptFrom   OBJECT-TYPE
        SYNTAX        OCTET STRING
        ACCESS        read-write
        STATUS        mandatory
        DESCRIPTION
        "This is a filter that describes the set of SSH client
        IP addresses and host names that can establish
        SSH connections to the MM authenticated by the public key
        represented by this entry of the table. The filter is a
        comma-separated list of IP addresses and/or hostnames.
        A question mark may be used to match any single character.
        An asterisk may be used to match multiple characters.
        An exclamation point may preceed an IP address or hostname
        to deny acccess from that IP address or hostname.

        The format of the Accept From specification is:
                    from=PATTERN-LIST
        PATTERN-LIST is the filter, which must be enclosed in
        double quotation marks.

        NOTE:This MIB object can be manipulated after the
        corresponding SSH public key is installed."
        ::= { mmSshClientAuthPubKeyEntry 6 }

    mmSshClientAuthPubKeyComment   OBJECT-TYPE
        SYNTAX        OCTET STRING
        ACCESS        read-write
        STATUS        mandatory
        DESCRIPTION
        "This is a descriptive string that the administrator may
        use to help identify the public key represented by this entry.
        It serves no function in the operation of the SSH server.

        NOTE:This MIB object can be manipulated after the
        corresponding SSH public key is installed."
        ::= { mmSshClientAuthPubKeyEntry 7 }

    mmSshClientAuthPubKeyAction    OBJECT-TYPE
        SYNTAX INTEGER {
          import(1),
          export(2)
        }
        ACCESS  read-write
        STATUS  mandatory
        DESCRIPTION
        "import(1) starts the TFTP file transfer of an SSH
        client authentication public key from the TFTP
        server to the MM. The import operation is only
        accepted if the associated RemoteAccessIdsEntry row
        is configured and the current value of
        mmSshClientAuthPubKeyEntryStatus is underCreation(3)
        or valid(1), if the current value of mmSshClientAuthPubKeyEntryStatus
        is valid(1), it will replace the key with a new key,
        If the import is successful the value of
        mmSshClientAuthPubKeyRowStatus changes to valid(1).
        export(2) starts the TFTP file transfer of an SSH
        client authentication public key from the MM to the TFTP
        server.  The export operation is only accepted if
        the current value of mmSshClientAuthPubKeyEntryStatus
        is valid(1).

        NOTE: Users should compare the fingerprint value
        mmSshClientAuthPubKeyFingerprint to the
        fingerprint of client authentication key files
        imported or exported using the TFTP file transfer
        protocol to guard against possible file corruption.

        Value returned for the GET command is meaningless
        for this MIB object."
        ::= { mmSshClientAuthPubKeyEntry 8 }

    mmSshClientAuthPubKeyEntryStatus     OBJECT-TYPE
        SYNTAX      EntryStatus
        ACCESS      read-write
        STATUS      mandatory
        DESCRIPTION
        "This object manages the creation and deletion of this entry.
        The steps recommended to install and to activate a new client
        authorization public key are:
        1. Set values for mmSshClientAuthPubKeyTftpServer,
           mmSshClientAuthPubKeyFileName, mmSshClientAuthPubKeyFileFormat
        2. Create a new entry in this table
           mmSshClientAuthPubKeyEntryStatus = createRequest
        3. Import a new key mmSshClientAuthPubKeyAction = import
           This entry will be valid after mmSshClientAuthPubKeyAction
           is successfully imported.
        4. Set mmSshClientAuthPubKeyAcceptFrom and
           mmSshClientAuthPubKeyComment as required.

        valid(1)        - Indicates that the public key pair represented
                          by this entry is available for use by the Secure
                          Shell Server for client authentication.

        createRequest(2) - A new entry will be created in this table
                           for the specified host key pair and the new
                           entry will transition to the underCreation(3)
                           state. The operation is only accepted if the
                           associated RemoteAccessIdsEntry row defining
                           a local user account is configured.

        underCreation(3) - Indicates that this entry exists in the
                           agent but is unavailable for use. After completing the
                           create operation, the agent will set this object to
                           underCreation(3).

        invalid(4)    - Deletes this entry and any client authentication
                        public key that may be associated with it.
         Note: only one row may be created at one time."
        ::= { mmSshClientAuthPubKeyEntry 9 }

    mmSshClientAuthPubKeyUserId  OBJECT-TYPE
                                    SYNTAX  OCTET STRING (SIZE(0..31))
                                    ACCESS  read-only
                                    STATUS  mandatory
                                    DESCRIPTION
                                    "The userid for the key entry."
                                    ::= { mmSshClientAuthPubKeyEntry 10 }


    mmSshClientAuthPubKeyUnused OBJECT-TYPE
                    SYNTAX  INTEGER
                    ACCESS  read-only
                    STATUS  mandatory
                    DESCRIPTION
                    "The number of available storage locations that may be
                    used to install additional Client Authentication
                    Public Keys. This number decreases by one when a new
                    key is added to the configuration."
                    ::= { mmSshClientAuth 2 }

    mmSshClientAuthPubKeyTftpServer   OBJECT-TYPE
                    SYNTAX  OCTET STRING
                    ACCESS  read-write
                    STATUS  mandatory
                    DESCRIPTION
                    "IP address or host name of the TFTP server where an SSH client
                    authentication public key is to be installed from or exported
                    to. The address must be entered in a dotted decimal
                    IP string (e.g. 9.37.44.2)."
                    ::= { mmSshClientAuth 3 }

    mmSshClientAuthPubKeyFileName      OBJECT-TYPE
                    SYNTAX  OCTET STRING
                    ACCESS  read-write
                    STATUS  mandatory
                    DESCRIPTION
                    "File name on the TFTP server of an SSH client
                    authentication public key."
                    ::= { mmSshClientAuth 4 }

    mmSshClientAuthPubKeyFileFormat      OBJECT-TYPE
                    SYNTAX    INTEGER {
                        openSSH (1),
                        rfc4716 (2)
                    }
                    ACCESS  read-write
                    STATUS  mandatory
                    DESCRIPTION
                    "File format of SSH client authentication public key files
                    imported from or exported to the TFTP file server."
                    ::= { mmSshClientAuth 5 }

    -- ********************************************************************************
    -- Group Profiles for LDAP Users
    -- ********************************************************************************
    groupProfiles  OBJECT IDENTIFIER ::= { remoteAccessConfig 7 }

    -- ********************************************************************************
    -- Group IDs Table
    -- ********************************************************************************
      groupIdsTable  OBJECT-TYPE
                            SYNTAX  SEQUENCE OF GroupIdsEntry
                            ACCESS  not-accessible
                            STATUS  mandatory
                            DESCRIPTION
                            "Table of Group profiles.

                            This table lets you to configure all group profiles.
                            You can define up to 16 unique profiles."
                            ::= {  groupProfiles 1 }

      groupIdsEntry  OBJECT-TYPE
                            SYNTAX GroupIdsEntry
                            ACCESS  not-accessible
                            STATUS  mandatory
                            DESCRIPTION
                            "Group ID entries."
                            INDEX { groupIndex }
                            ::= { groupIdsTable 1 }

      GroupIdsEntry ::= SEQUENCE {
                   groupIndex INTEGER,
                   groupId OCTET STRING,
                   groupRole OCTET STRING,
                   groupEntryStatus EntryStatus
                   }

      groupIndex  OBJECT-TYPE
                            SYNTAX  INTEGER(0..255)
                            ACCESS  read-only
                            STATUS  mandatory
                            DESCRIPTION
                            "Index for Group IDs entry."
                            ::= { groupIdsEntry 1 }

      groupId  OBJECT-TYPE
                            SYNTAX  OCTET STRING (SIZE(0..16))
                            ACCESS  read-write
                            STATUS  mandatory
                            DESCRIPTION
                            "Group ID. It is a null terminated string that contains the group-id.
                            It must not be a duplicate of any previously configured ones."
                            ::= { groupIdsEntry 2 }

      groupRole  OBJECT-TYPE
                            SYNTAX  OCTET STRING
                            ACCESS  read-only
                            STATUS  mandatory
                            DESCRIPTION
                            "Group Role. It indicates if the group has supervisor, operator,
                            or custom access."
                            ::= { groupIdsEntry 3 }

      groupEntryStatus  OBJECT-TYPE
                            SYNTAX      EntryStatus
                            ACCESS      read-write
                            STATUS      mandatory
                            DESCRIPTION
                            "This object manages the creation and deletion of this entry.
                            The steps recommended to add a new group are:
                                1. Create a new entry in this table
                                   groupEntryStatus = createRequest
                                2. Set groupId as required.
                                   Then the entry will be valid.

                            valid(1)         - Indicates that the group represented
                                               by this entry is available for use.

                            createRequest(2) - A new entry will be created in this table
                                               for the specified group and the new entry
                                               will transition to the underCreation(3).

                            underCreation(3) - Indicates that this entry exists in the
                                               agent but is unavailable for use. After completing the
                                               create operation, the agent will set this object to
                                               underCreation(3).

                            invalid(4)       - Deletes this entry."
                            ::= { groupIdsEntry 9 }

    -- ********************************************************************************
    -- Group Role Table
    -- ********************************************************************************
      groupRBSroleTable  OBJECT-TYPE
                    SYNTAX  SEQUENCE OF GroupRBSroleEntry
                    ACCESS  not-accessible
                    STATUS  mandatory
                    DESCRIPTION
                    "Table of Group Role profiles."
                    ::= {  groupProfiles 2 }

      groupRBSroleEntry  OBJECT-TYPE
                    SYNTAX GroupRBSroleEntry
                    ACCESS  not-accessible
                    STATUS  mandatory
                    DESCRIPTION
                    "Group Role entries."
                    INDEX { groupRBSroleIndex }
                    ::= { groupRBSroleTable 1 }

      GroupRBSroleEntry ::= SEQUENCE {
                    groupRBSroleIndex INTEGER,
                    groupRBSroleId OCTET STRING,
                    groupRBSSupervisor INTEGER,
                    groupRBSOperator INTEGER,
                    groupRBSChassisOperator INTEGER,
                    groupRBSChassisAccountManagement INTEGER,
                    groupRBSChassisLogManagement INTEGER,
                    groupRBSChassisConfiguration INTEGER,
                    groupRBSChassisAdministration INTEGER,
                    groupRBSBladeOperator INTEGER,
                    groupRBSBladeRemotePresence INTEGER,
                    groupRBSBladeConfiguration INTEGER,
                    groupRBSBladeAdministration INTEGER,
                    groupRBSSwitchModuleOperator INTEGER,
                    groupRBSSwitchModuleConfiguration INTEGER,
                    groupRBSSwitchModuleAdministration INTEGER
                    }

      groupRBSroleIndex  OBJECT-TYPE
                    SYNTAX  INTEGER(0..255)
                    ACCESS  read-only
                    STATUS  mandatory
                    DESCRIPTION
                    "Index for Group Role entry."
                    ::= { groupRBSroleEntry 1 }

      groupRBSroleId  OBJECT-TYPE
                    SYNTAX  OCTET STRING (SIZE(0..16))
                    ACCESS  read-only
                    STATUS  mandatory
                    DESCRIPTION
                    "Group ID"
                    ::= { groupRBSroleEntry 2 }

      groupRBSSupervisor  OBJECT-TYPE
                    SYNTAX  INTEGER {
                       disabled(0),
                       enabled(1)
                    }
                    ACCESS  read-write
                    STATUS  mandatory
                    DESCRIPTION
                    "Group has no restrictions."
                    ::= { groupRBSroleEntry 3 }

      groupRBSOperator OBJECT-TYPE
                    SYNTAX  INTEGER {
                       disabled(0),
                       enabled(1)
                    }
                    ACCESS  read-write
                    STATUS  mandatory
                    DESCRIPTION
                    "Group has read-only access, and cannot perform
                    any save, modify, clear, or state affecting operations
                    (e.g. restart MM, restore defaults, upgrade the firmware, etc.)."
                    ::= { groupRBSroleEntry 4 }

      groupRBSChassisOperator OBJECT-TYPE
                    SYNTAX  INTEGER {
                       disabled(0),
                       enabled(1)
                    }
                    ACCESS  read-write
                    STATUS  mandatory
                    DESCRIPTION
                    "Group has ability to browse status and properties of
                    chassis components (MM, chassis fans, midplane, power modules).
                    Ability to backup MM configuration to a file.
                    Saving MM configuration to chassis requires supervisor access."
                    ::= { groupRBSroleEntry 5 }

      groupRBSChassisAccountManagement  OBJECT-TYPE
                    SYNTAX  INTEGER {
                       disabled(0),
                       enabled(1)
                    }
                    ACCESS  read-write
                    STATUS  mandatory
                    DESCRIPTION
                    "Group can add/modify/delete user login profiles. Ability
                    to backup MM configuration to a file. Changing global login
                    settings require chassis configuration authority."
                    ::= { groupRBSroleEntry 6 }

      groupRBSChassisLogManagement  OBJECT-TYPE
                    SYNTAX  INTEGER {
                       disabled(0),
                       enabled(1)
                    }
                    ACCESS  read-write
                    STATUS  mandatory
                    DESCRIPTION
                    "Group has ability to clear the MM event log, change log
                    policy settings, and backup MM configuration to a file."
                    ::= { groupRBSroleEntry 7 }

      groupRBSChassisConfiguration  OBJECT-TYPE
                    SYNTAX  INTEGER {
                       disabled(0),
                       enabled(1)
                    }
                    ACCESS  read-write
                    STATUS  mandatory
                    DESCRIPTION
                    "Group can modify and save any chassis configuration
                    parameter (except user profiles and event log settings).
                    Ability to restore MM factory defaults if the group also has
                    chassis administration permissions. Ability to change the
                    global login settings, SOL configuration, and backup MM
                    configuration to a file."
                    ::= { groupRBSroleEntry 8 }

      groupRBSChassisAdministration  OBJECT-TYPE
                    SYNTAX  INTEGER {
                       disabled(0),
                       enabled(1)
                    }
                    ACCESS  read-write
                    STATUS  mandatory
                    DESCRIPTION
                    "Group has ability to do MM firmware updates, modify chassis
                    LEDs, restore MM factory defaults if the group also has
                    chassis configuration permissions. Ability to restart MM
                    and backup MM configuration to a file."
                    ::= { groupRBSroleEntry 9 }

      groupRBSBladeOperator  OBJECT-TYPE
                    SYNTAX  INTEGER {
                       disabled(0),
                       enabled(1)
                    }
                    ACCESS  read-write
                    STATUS  mandatory
                    DESCRIPTION
                    "Group has ability to browse status and properties of
                    blades."
                    ::= { groupRBSroleEntry 10 }

      groupRBSBladeRemotePresence  OBJECT-TYPE
                    SYNTAX  INTEGER {
                       disabled(0),
                       enabled(1)
                    }
                    ACCESS  read-write
                    STATUS  mandatory
                    DESCRIPTION
                    "Group has ability to access the blade remote console
                    The ability to issue the CLI
                    console command to start an SOL session to a blade will
                    also require this authority."
                    ::= { groupRBSroleEntry 11 }

      groupRBSBladeConfiguration  OBJECT-TYPE
                    SYNTAX  INTEGER {
                       disabled(0),
                       enabled(1)
                    }
                    ACCESS  read-write
                    STATUS  mandatory
                    DESCRIPTION
                    "Group can modify and save any blade configuration parameter."
                    ::= { groupRBSroleEntry 12 }

      groupRBSBladeAdministration  OBJECT-TYPE
                    SYNTAX  INTEGER {
                       disabled(0),
                       enabled(1)
                    }
                    ACCESS  read-write
                    STATUS  mandatory
                    DESCRIPTION
                    "Group can power on/off and restart blades, activate
                    standby blades, do firmware updates, and modify blade LEDs."
                    ::= { groupRBSroleEntry 13 }

      groupRBSSwitchModuleOperator  OBJECT-TYPE
                    SYNTAX  INTEGER {
                       disabled(0),
                       enabled(1)
                    }
                    ACCESS  read-write
                    STATUS  mandatory
                    DESCRIPTION
                    "Group has ability to browse status and properties of
                    I/O Modules, and to ping I/O Modules."
                    ::= { groupRBSroleEntry 14 }

      groupRBSSwitchModuleConfiguration  OBJECT-TYPE
                    SYNTAX  INTEGER {
                       disabled(0),
                       enabled(1)
                    }
                    ACCESS  read-write
                    STATUS  mandatory
                    DESCRIPTION
                    "Group can modify the I/O Module IP address, configure
                    I/O Module Advanced Management parameters, and restore
                    factory defaults on an I/O Module. Note that a group
                    requires both I/O Module configuration and I/O Module
                    administration roles in order to be able to launch a telnet
                    session to an I/O Module, or to restore factory
                    defaults on an I/O Module."
                    ::= { groupRBSroleEntry 15 }

      groupRBSSwitchModuleAdministration  OBJECT-TYPE
                    SYNTAX  INTEGER {
                       disabled(0),
                       enabled(1)
                    }
                    ACCESS  read-write
                    STATUS  mandatory
                    DESCRIPTION
                    "Group can power on/off and restart the I/O Modules,
                    update I/O Module firmware, enable/disable the Fast POST
                    and External Ports of an I/O Module. Note that a group
                    requires both I/O Module configuration and I/O Module
                    administration roles in order to be able to launch a telnet
                    session to an I/O Module, or to restore factory
                    defaults on an I/O Module."
                    ::= { groupRBSroleEntry 16 }

    -- ********************************************************************************
    -- Group Scope Table
    -- ********************************************************************************
      groupRBSscopeTable  OBJECT-TYPE
                    SYNTAX  SEQUENCE OF GroupRBSscopeEntry
                    ACCESS  not-accessible
                    STATUS  mandatory
                    DESCRIPTION
                    "Table of Group Scope profiles."
                    ::= {  groupProfiles 3 }

      groupRBSscopeEntry  OBJECT-TYPE
                    SYNTAX GroupRBSscopeEntry
                    ACCESS  not-accessible
                    STATUS  mandatory
                    DESCRIPTION
                    "Group Scope entries."
                    INDEX { groupRBSscopeIndex }
                    ::= { groupRBSscopeTable 1 }

      GroupRBSscopeEntry ::= SEQUENCE {
                    groupRBSscopeIndex INTEGER,
                    groupRBSscopeId OCTET STRING,
                    groupRBSChassis INTEGER,
                    groupRBSBlade1 INTEGER,
                    groupRBSBlade2 INTEGER,
                    groupRBSBlade3 INTEGER,
                    groupRBSBlade4 INTEGER,
                    groupRBSBlade5 INTEGER,
                    groupRBSBlade6 INTEGER,
                    groupRBSBlade7 INTEGER,
                    groupRBSBlade8 INTEGER,
                    groupRBSBlade9 INTEGER,
                    groupRBSBlade10 INTEGER,
                    groupRBSBlade11 INTEGER,
                    groupRBSBlade12 INTEGER,
                    groupRBSBlade13 INTEGER,
                    groupRBSBlade14 INTEGER,
                    groupRBSSwitch1 INTEGER,
                    groupRBSSwitch2 INTEGER,
                    groupRBSSwitch3 INTEGER,
                    groupRBSSwitch4 INTEGER,
                    groupRBSSwitch5 INTEGER,
                    groupRBSSwitch6 INTEGER,
                    groupRBSSwitch7 INTEGER,
                    groupRBSSwitch8 INTEGER,
                    groupRBSSwitch9 INTEGER,
                    groupRBSSwitch10 INTEGER
                    }


      groupRBSscopeIndex    OBJECT-TYPE
                    SYNTAX  INTEGER(0..255)
                    ACCESS  read-only
                    STATUS  mandatory
                    DESCRIPTION
                    "Index for Group Scope Entry."
                    ::= { groupRBSscopeEntry 1 }

      groupRBSscopeId       OBJECT-TYPE
                    SYNTAX  OCTET STRING (SIZE(0..16))
                    ACCESS  read-only
                    STATUS  mandatory
                    DESCRIPTION
                    "Group ID"
                    ::= { groupRBSscopeEntry 2 }

      groupRBSChassis    OBJECT-TYPE
                    SYNTAX  INTEGER {
                       disabled(0),
                       enabled(1)
                    }
                    ACCESS  read-write
                    STATUS  mandatory
                    DESCRIPTION
                    "Group has access to the MM and chassis functions."
                    ::= { groupRBSscopeEntry 3 }

      groupRBSBlade1     OBJECT-TYPE
                    SYNTAX  INTEGER {
                       disabled(0),
                       enabled(1)
                    }
                    ACCESS  read-write
                    STATUS  mandatory
                    DESCRIPTION
                    "Group has access to the blade in slot 1."
                    ::= { groupRBSscopeEntry 4 }

      groupRBSBlade2     OBJECT-TYPE
                    SYNTAX  INTEGER {
                       disabled(0),
                       enabled(1)
                    }
                    ACCESS  read-write
                    STATUS  mandatory
                    DESCRIPTION
                    "Group has access to the blade in slot 2."
                    ::= { groupRBSscopeEntry 5 }

      groupRBSBlade3     OBJECT-TYPE
                    SYNTAX  INTEGER {
                       disabled(0),
                       enabled(1)
                    }
                    ACCESS  read-write
                    STATUS  mandatory
                    DESCRIPTION
                    "Group has access to the blade in slot 3."
                    ::= { groupRBSscopeEntry 6 }

      groupRBSBlade4     OBJECT-TYPE
                    SYNTAX  INTEGER {
                       disabled(0),
                       enabled(1)
                    }
                    ACCESS  read-write
                    STATUS  mandatory
                    DESCRIPTION
                    "Group has access to the blade in slot 4."
                    ::= { groupRBSscopeEntry 7 }

      groupRBSBlade5     OBJECT-TYPE
                    SYNTAX  INTEGER {
                       disabled(0),
                       enabled(1)
                    }
                    ACCESS  read-write
                    STATUS  mandatory
                    DESCRIPTION
                    "Group has access to the blade in slot 5."
                    ::= { groupRBSscopeEntry 8 }

      groupRBSBlade6     OBJECT-TYPE
                    SYNTAX  INTEGER {
                       disabled(0),
                       enabled(1)
                    }
                    ACCESS  read-write
                    STATUS  mandatory
                    DESCRIPTION
                    "Group has access to the blade in slot 6."
                    ::= { groupRBSscopeEntry 9 }

      groupRBSBlade7     OBJECT-TYPE
                    SYNTAX  INTEGER {
                       disabled(0),
                       enabled(1)
                    }
                    ACCESS  read-write
                    STATUS  mandatory
                    DESCRIPTION
                    "Group has access to the blade in slot 7."
                    ::= { groupRBSscopeEntry 10 }

      groupRBSBlade8     OBJECT-TYPE
                    SYNTAX  INTEGER {
                       disabled(0),
                       enabled(1)
                    }
                    ACCESS  read-write
                    STATUS  mandatory
                    DESCRIPTION
                    "Group has access to the blade in slot 8."
                    ::= { groupRBSscopeEntry 11 }

      groupRBSBlade9     OBJECT-TYPE
                    SYNTAX  INTEGER {
                       disabled(0),
                       enabled(1)
                    }
                    ACCESS  read-write
                    STATUS  mandatory
                    DESCRIPTION
                    "Group has access to the blade in slot 9."
                    ::= { groupRBSscopeEntry 12 }

      groupRBSBlade10    OBJECT-TYPE
                    SYNTAX  INTEGER {
                       disabled(0),
                       enabled(1)
                    }
                    ACCESS  read-write
                    STATUS  mandatory
                    DESCRIPTION
                    "Group has access to the blade in slot 10."
                    ::= { groupRBSscopeEntry 13 }

      groupRBSBlade11    OBJECT-TYPE
                    SYNTAX  INTEGER {
                       disabled(0),
                       enabled(1)
                    }
                    ACCESS  read-write
                    STATUS  mandatory
                    DESCRIPTION
                    "Group has access to the blade in slot 11."
                    ::= { groupRBSscopeEntry 14 }

      groupRBSBlade12    OBJECT-TYPE
                    SYNTAX  INTEGER {
                       disabled(0),
                       enabled(1)
                    }
                    ACCESS  read-write
                    STATUS  mandatory
                    DESCRIPTION
                    "Group has access to the blade in slot 12."
                    ::= { groupRBSscopeEntry 15 }

      groupRBSBlade13    OBJECT-TYPE
                    SYNTAX  INTEGER {
                       disabled(0),
                       enabled(1)
                    }
                    ACCESS  read-write
                    STATUS  mandatory
                    DESCRIPTION
                    "Group has access to the blade in slot 13."
                    ::= { groupRBSscopeEntry 16 }

      groupRBSBlade14    OBJECT-TYPE
                    SYNTAX  INTEGER {
                       disabled(0),
                       enabled(1)
                    }
                    ACCESS  read-write
                    STATUS  mandatory
                    DESCRIPTION
                    "Group has access to the blade in slot 14."
                    ::= { groupRBSscopeEntry 17 }

      groupRBSSwitch1    OBJECT-TYPE
                    SYNTAX  INTEGER {
                       disabled(0),
                       enabled(1)
                    }
                    ACCESS  read-write
                    STATUS  mandatory
                    DESCRIPTION
                    "Group has access to I/O module 1."
                    ::= { groupRBSscopeEntry 18 }

      groupRBSSwitch2    OBJECT-TYPE
                    SYNTAX  INTEGER {
                       disabled(0),
                       enabled(1)
                    }
                    ACCESS  read-write
                    STATUS  mandatory
                    DESCRIPTION
                    "Group has access to I/O module 2."
                    ::= { groupRBSscopeEntry 19 }

      groupRBSSwitch3    OBJECT-TYPE
                    SYNTAX  INTEGER {
                       disabled(0),
                       enabled(1)
                    }
                    ACCESS  read-write
                    STATUS  mandatory
                    DESCRIPTION
                    "Group has access to I/O module 3."
                    ::= { groupRBSscopeEntry 20 }

      groupRBSSwitch4    OBJECT-TYPE
                    SYNTAX  INTEGER {
                       disabled(0),
                       enabled(1)
                    }
                    ACCESS  read-write
                    STATUS  mandatory
                    DESCRIPTION
                    "Group has access to I/O module 4."
                    ::= { groupRBSscopeEntry 21 }

      groupRBSSwitch5    OBJECT-TYPE
                    SYNTAX  INTEGER {
                       disabled(0),
                       enabled(1)
                    }
                    ACCESS  read-write
                    STATUS  mandatory
                    DESCRIPTION
                    "Group has access to I/O module 5."
                    ::= { groupRBSscopeEntry 22 }

      groupRBSSwitch6    OBJECT-TYPE
                    SYNTAX  INTEGER {
                       disabled(0),
                       enabled(1)
                    }
                    ACCESS  read-write
                    STATUS  mandatory
                    DESCRIPTION
                    "Group has access to I/O module 6."
                    ::= { groupRBSscopeEntry 23 }

      groupRBSSwitch7    OBJECT-TYPE
                    SYNTAX  INTEGER {
                       disabled(0),
                       enabled(1)
                    }
                    ACCESS  read-write
                    STATUS  mandatory
                    DESCRIPTION
                    "Group has access to I/O module 7."
                    ::= { groupRBSscopeEntry 24 }

      groupRBSSwitch8    OBJECT-TYPE
                    SYNTAX  INTEGER {
                       disabled(0),
                       enabled(1)
                    }
                    ACCESS  read-write
                    STATUS  mandatory
                    DESCRIPTION
                    "Group has access to I/O module 8."
                    ::= { groupRBSscopeEntry 25 }

      groupRBSSwitch9     OBJECT-TYPE
                    SYNTAX  INTEGER {
                       disabled(0),
                       enabled(1)
                    }
                    ACCESS  read-write
                    STATUS  mandatory
                    DESCRIPTION
                    "Group has access to I/O module 9."
                    ::= { groupRBSscopeEntry 26 }

      groupRBSSwitch10    OBJECT-TYPE
                    SYNTAX  INTEGER {
                       disabled(0),
                       enabled(1)
                    }
                    ACCESS  read-write
                    STATUS  mandatory
                    DESCRIPTION
                    "Group has access to I/O module 10."
                    ::= { groupRBSscopeEntry 27 }

    -- ********************************************************************************
    -- Remote Alert types
    -- ********************************************************************************
    remoteAlerts  OBJECT IDENTIFIER ::= { configureSP 2 }

     -- ********************************************************************************
     -- Remote Alert Critical Error types
     -- ********************************************************************************
     remoteAlertsCrit  OBJECT IDENTIFIER ::= { remoteAlerts 1 }

      critPower    OBJECT-TYPE
                   SYNTAX  INTEGER {
                     disabled(0),
                     enabled(1)
                   }
                   ACCESS  read-write
                   STATUS  mandatory
                   DESCRIPTION
                   "Generate an alert if any of the system power supplies fail."
                   ::= { remoteAlertsCrit 5 }

      critBlade  OBJECT-TYPE
                   SYNTAX  INTEGER {
                     disabled(0),
                     enabled(1)
                   }
                   ACCESS  read-write
                   STATUS  mandatory
                   DESCRIPTION
                   "Generate an alert for any critical error condition on a blade."
                   ::= { remoteAlertsCrit 10 }

      critIO  OBJECT-TYPE
                   SYNTAX  INTEGER {
                     disabled(0),
                     enabled(1)
                   }
                   ACCESS  read-write
                   STATUS  mandatory
                   DESCRIPTION
                   "Generate an alert for any critical error condition on I/O module."
                   ::= { remoteAlertsCrit 11 }

      critStorage  OBJECT-TYPE
                   SYNTAX  INTEGER {
                     disabled(0),
                     enabled(1)
                   }
                   ACCESS  read-write
                   STATUS  mandatory
                   DESCRIPTION
                   "Generate an alert for any critical error condition on a Storage module."
                   ::= { remoteAlertsCrit 12 }

      critChassis  OBJECT-TYPE
                   SYNTAX  INTEGER {
                     disabled(0),
                     enabled(1)
                   }
                   ACCESS  read-write
                   STATUS  mandatory
                   DESCRIPTION
                   "Generate an alert for any critical error condition on chassis."
                   ::= { remoteAlertsCrit 13 }

      critFan  OBJECT-TYPE
                   SYNTAX  INTEGER {
                     disabled(0),
                     enabled(1)
                   }
                   ACCESS  read-write
                   STATUS  mandatory
                   DESCRIPTION
                   "Generate an alert for any critical error condition on cooling devices."
                   ::= { remoteAlertsCrit 14 }

     -- ********************************************************************************
     -- Remote Alert Warning(non-critical) Error types
     -- ********************************************************************************
     remoteAlertsNonCrit  OBJECT IDENTIFIER ::= { remoteAlerts 2 }

      warnLogFull  OBJECT-TYPE
                   SYNTAX  INTEGER {
                     disabled(0),
                     enabled(1)
                   }
                   ACCESS  read-write
                   STATUS  mandatory
                   DESCRIPTION
                   "Generate an alert if the system log reaches 100% full."
                   ::= { remoteAlertsNonCrit 10 }

      warnBlade  OBJECT-TYPE
                   SYNTAX  INTEGER {
                     disabled(0),
                     enabled(1)
                   }
                   ACCESS  read-write
                   STATUS  mandatory
                   DESCRIPTION
                   "Generate an alert for any warning condition on a blade."
                   ::= {  remoteAlertsNonCrit 15 }

      warnIO  OBJECT-TYPE
                   SYNTAX  INTEGER {
                     disabled(0),
                     enabled(1)
                   }
                   ACCESS  read-write
                   STATUS  mandatory
                   DESCRIPTION
                   "Generate an alert for any warning condition on I/O module."
                   ::= {  remoteAlertsNonCrit 16 }

      warnStorage  OBJECT-TYPE
                   SYNTAX  INTEGER {
                     disabled(0),
                     enabled(1)
                   }
                   ACCESS  read-write
                   STATUS  mandatory
                   DESCRIPTION
                   "Generate an alert for any warning condition on a Storage module."
                   ::= {  remoteAlertsNonCrit 17 }

      warnPower  OBJECT-TYPE
                   SYNTAX  INTEGER {
                     disabled(0),
                     enabled(1)
                   }
                   ACCESS  read-write
                   STATUS  mandatory
                   DESCRIPTION
                   "Generate an alert for any warning condition on power module."
                   ::= {  remoteAlertsNonCrit 18 }

      warnChassis  OBJECT-TYPE
                   SYNTAX  INTEGER {
                     disabled(0),
                     enabled(1)
                   }
                   ACCESS  read-write
                   STATUS  mandatory
                   DESCRIPTION
                   "Generate an alert for any warning condition on chassis."
                   ::= {  remoteAlertsNonCrit 19 }

      warnFan  OBJECT-TYPE
                   SYNTAX  INTEGER {
                     disabled(0),
                     enabled(1)
                   }
                   ACCESS  read-write
                   STATUS  mandatory
                   DESCRIPTION
                   "Generate an alert for any warning condition on cooling devices."
                   ::= {  remoteAlertsNonCrit 20 }

     -- ********************************************************************************
     -- Remote Alert System Error types
     -- ********************************************************************************
     remoteAlertsSystem  OBJECT IDENTIFIER ::= { remoteAlerts 3 }

      systemInventory  OBJECT-TYPE
                   SYNTAX  INTEGER {
                     disabled(0),
                     enabled(1)
                   }
                   ACCESS  read-write
                   STATUS  mandatory
                   DESCRIPTION
                   "Generate an alert if the a processor blade or media tray is
                   added or removed."
                   ::= {  remoteAlertsSystem 10 }

      systemLog75PctFull  OBJECT-TYPE
                   SYNTAX  INTEGER {
                     disabled(0),
                     enabled(1)
                   }
                   ACCESS  read-write
                   STATUS  mandatory
                   DESCRIPTION
                   "Generate an alert if the system log reaches 75% full."
                   ::= {  remoteAlertsSystem 11 }

      networkChangeNotification OBJECT-TYPE
                   SYNTAX  INTEGER {
                     disabled(0),
                     enabled(1)
                   }
                   ACCESS  read-write
                   STATUS  mandatory
                   DESCRIPTION
                   "Generate an alert if the MM has restarted and the internal
                   network has initialized successfully, or if an IP address
                   change via a source other than the management module."
                   ::= {  remoteAlertsSystem 12 }

      systemRemoteLogin  OBJECT-TYPE
                   SYNTAX  INTEGER {
                     disabled(0),
                     enabled(1)
                   }
                   ACCESS  read-write
                   STATUS  mandatory
                   DESCRIPTION
                   "Generate an alert if the system detects a new user logged in from
                   a remote site."
                   ::= {  remoteAlertsSystem 15 }

      systemBlade  OBJECT-TYPE
                   SYNTAX  INTEGER {
                     disabled(0),
                     enabled(1)
                   }
                   ACCESS  read-write
                   STATUS  mandatory
                   DESCRIPTION
                   "Generate an alert for any informational condition on a blade."
                   ::= {  remoteAlertsSystem 16 }

      systemIO  OBJECT-TYPE
                   SYNTAX  INTEGER {
                     disabled(0),
                     enabled(1)
                   }
                   ACCESS  read-write
                   STATUS  mandatory
                   DESCRIPTION
                   "Generate an alert for any informational condition on I/O module."
                   ::= {  remoteAlertsSystem 17 }

      systemStorage  OBJECT-TYPE
                   SYNTAX  INTEGER {
                     disabled(0),
                     enabled(1)
                   }
                   ACCESS  read-write
                   STATUS  mandatory
                   DESCRIPTION
                   "Generate an alert for any informational condition on a Storage module."
                   ::= {  remoteAlertsSystem 18 }

      systemPower  OBJECT-TYPE
                   SYNTAX  INTEGER {
                     disabled(0),
                     enabled(1)
                   }
                   ACCESS  read-write
                   STATUS  mandatory
                   DESCRIPTION
                   "Generate an alert for any informational condition on power module."
                   ::= {  remoteAlertsSystem 19 }

      systemChassis  OBJECT-TYPE
                   SYNTAX  INTEGER {
                     disabled(0),
                     enabled(1)
                   }
                   ACCESS  read-write
                   STATUS  mandatory
                   DESCRIPTION
                   "Generate an alert for any informational condition on chassis."
                   ::= {  remoteAlertsSystem 20}

      systemFan  OBJECT-TYPE
                   SYNTAX  INTEGER {
                     disabled(0),
                     enabled(1)
                   }
                   ACCESS  read-write
                   STATUS  mandatory
                   DESCRIPTION
                   "Generate an alert for any informational condition on cooling device."
                   ::= {  remoteAlertsSystem 21}

      systemPWRDO  OBJECT-TYPE
                   SYNTAX  INTEGER {
                     disabled(0),
                     enabled(1)
                   }
                   ACCESS  read-write
                   STATUS  mandatory
                   DESCRIPTION
                   "Generate an alert for any informational condition on power on and power off."
                   ::= {  remoteAlertsSystem 22}

     -- ********************************************************************************
     -- Users
     -- ********************************************************************************
     --
     users  OBJECT IDENTIFIER ::= { monitors 17 }

      -- ********************************************************************************
      -- MM Users
      -- ********************************************************************************
      --
      mmUsers  OBJECT IDENTIFIER ::= { users 1 }

       currentlyLoggedInTable  OBJECT-TYPE
                     SYNTAX  SEQUENCE OF CurrentlyLoggedInEntry
                     ACCESS  not-accessible
                     STATUS  mandatory
                     DESCRIPTION
                     "Table of MM users currently logged in."
                     ::= {  mmUsers 1 }

       currentlyLoggedInEntry  OBJECT-TYPE
                     SYNTAX CurrentlyLoggedInEntry
                     ACCESS  not-accessible
                     STATUS  mandatory
                     DESCRIPTION
                     "MM users currently logged in entries."
                     INDEX { currentlyLoggedInEntryIndex }
                     ::= { currentlyLoggedInTable 1 }

       CurrentlyLoggedInEntry ::= SEQUENCE {
                    currentlyLoggedInEntryIndex INTEGER,
                    currentlyLoggedInEntryUserId OCTET STRING,
                    currentlyLoggedInEntryAccMethod OCTET STRING
                    }

       currentlyLoggedInEntryIndex  OBJECT-TYPE
                          SYNTAX  INTEGER(0..255)
                          ACCESS  read-only
                          STATUS  mandatory
                          DESCRIPTION
                          "Index for MM users currently logged in."
                          ::= { currentlyLoggedInEntry 1 }

       currentlyLoggedInEntryUserId   OBJECT-TYPE
                          SYNTAX  OCTET STRING (SIZE(0..64))
                          ACCESS  read-only
                          STATUS  mandatory
                           DESCRIPTION
                          "Name for MM users currently logged in.
                          NOTE: 'Default SNMPv1 user' indicates an internal user used by SNMPv1 agent."
                          ::= { currentlyLoggedInEntry 2 }

       currentlyLoggedInEntryAccMethod  OBJECT-TYPE
                          SYNTAX  OCTET STRING (SIZE(0..32))
                          ACCESS  read-only
                          STATUS  mandatory
                          DESCRIPTION
                          "Access method for MM users currently logged in."
                          ::= { currentlyLoggedInEntry 3 }

     -- ********************************************************************************
     -- Vital Product Data(VPD) information
     --
     -- ATTENTION !!!!!!
     --
     -- All data under the vpdInformation anchor is deprecated and should not be used, 
     -- with the exception of these tables:
     -- 
     --    bladeMACAddressVpdTable               { bladeHardwareVpd 2 }
     --
     --    inventoryManagementActivityVpdTable   { vpdInformation 22 }
     --
     --    bladeAndExpCardWwnGuidVpdTable        { bladeHardwareVpd 7 }
     --
     -- All applications and scripts should be changed to migrate toward using the 
     -- new component based tables for hardware and firmware inventory under this anchor:
     --
     --  componentInformation  OBJECT IDENTIFIER ::= { monitors 23 }
     --
     -- The objects under the vpdInformation section will be maintained on an "as-is"  
     -- basis and will not be enhanced. They are included as a convenience for 
     -- users migrating from a legacy BladeCenter chassis environment. 
     --
     -- Not all components in the Flex chassis are guaranteed to be present in these 
     -- old deprecated objects. 
     --
     -- ********************************************************************************
     vpdInformation  OBJECT IDENTIFIER ::= { monitors 21 }

      -- ********************************************************************************
      -- Chassis VPD
      -- ********************************************************************************
      chassisInfoVpd OBJECT IDENTIFIER ::= { vpdInformation 1 }

       chassisVpd OBJECT IDENTIFIER ::= { chassisInfoVpd 1 }

        chassisVpdMachineType OBJECT-TYPE
                      SYNTAX  OCTET STRING
                      ACCESS  read-write
                      STATUS  deprecated
                      DESCRIPTION
                      "Machine type VPD information (from System BIOS).  This field must be four
                      alpha numeric characters."
                      ::= { chassisVpd 1 }

        chassisVpdMachineModel OBJECT-TYPE
                      SYNTAX  OCTET STRING
                      ACCESS  read-write
                      STATUS  deprecated
                      DESCRIPTION
                      "Machine model VPD information (from System BIOS).  This field  must be three
                      alpha numeric characters."
                      ::= { chassisVpd 2 }

        chassisSerialNumber OBJECT-TYPE
                      SYNTAX  OCTET STRING
                      ACCESS  read-write
                      STATUS  deprecated
                      DESCRIPTION
                      "Machine serial number VPD information (from System BIOS).  This field must be
                      seven alpha numeric characters."
                      ::= { chassisVpd 3 }

        chassisUUID OBJECT-TYPE
                      SYNTAX  OCTET STRING
                      ACCESS  read-write
                      STATUS  deprecated
                      DESCRIPTION
                      "Machine UUID (Universal Unique ID information) (from System BIOS).  This field
                      must be 32 alpha numeric characters."
                      ::= { chassisVpd 4 }

        chassisManufacturingId OBJECT-TYPE
                      SYNTAX  OCTET STRING
                      ACCESS  read-only
                      STATUS  deprecated
                      DESCRIPTION
                      "Machine chassis manufacturing ID."
                      ::= { chassisVpd 5 }

        chassisHardwareRevision OBJECT-TYPE
                      SYNTAX  INTEGER
                      ACCESS  read-only
                      STATUS  deprecated
                      DESCRIPTION
                      "Machine chassis hardware revision.
                       If a hardware revision is programmed in the OEM VPD area for this component,
                       then the HardwareRevisionString version of this MIB object should be used."
                      ::= { chassisVpd 6 }

        chassisFruNumber OBJECT-TYPE
                      SYNTAX  OCTET STRING
                      ACCESS  read-only
                      STATUS  deprecated
                      DESCRIPTION
                      "Machine chassis FRU number."
                      ::= { chassisVpd 7 }

        chassisManufDate OBJECT-TYPE
                      SYNTAX  OCTET STRING
                      ACCESS  read-only
                      STATUS  deprecated
                      DESCRIPTION
                      "Machine chassis manufacture date."
                      ::= { chassisVpd 8 }

        chassisPartNumber OBJECT-TYPE
                      SYNTAX  OCTET STRING
                      ACCESS  read-only
                      STATUS  deprecated
                      DESCRIPTION
                      "Machine chassis part number."
                      ::= { chassisVpd 9 }

        chassisFruSerial OBJECT-TYPE
                      SYNTAX  OCTET STRING
                      ACCESS  read-only
                      STATUS  deprecated
                      DESCRIPTION
                      "Machine chassis FRU serial number."
                      ::= { chassisVpd 10 }

        chassisManufacturingIDNumber OBJECT-TYPE
                      SYNTAX  OCTET STRING
                      ACCESS  read-only
                      STATUS  deprecated
                      DESCRIPTION
                      "Machine chassis manufacturer ID Number."
                      ::= { chassisVpd 11 }

        chassisProductId OBJECT-TYPE
                      SYNTAX  OCTET STRING
                      ACCESS  read-only
                      STATUS  deprecated
                      DESCRIPTION
                      "Machine chassis product ID."
                      ::= { chassisVpd 12 }

        chassisSubManufacturerId OBJECT-TYPE
                      SYNTAX  OCTET STRING
                      ACCESS  read-only
                      STATUS  deprecated
                      DESCRIPTION
                      "Machine chassis subsystem manufacturer."
                      ::= { chassisVpd 13 }

        chassisClei OBJECT-TYPE
                      SYNTAX  OCTET STRING
                      ACCESS  read-only
                      STATUS  deprecated
                      DESCRIPTION
                      "Machine chassis Common Language Equipment Identification (CLEI)."
                      ::= { chassisVpd 14 }

        chassisHardwareRevisionString OBJECT-TYPE
                      SYNTAX  OCTET STRING
                      ACCESS  read-only
                      STATUS  deprecated
                      DESCRIPTION
                      "Machine chassis hardware revision in string format.
                       If a hardware revision is programmed in the OEM VPD area for this component,
                       then this MIB object should be used."
                      ::= { chassisVpd 16 }

      -- ********************************************************************************
      -- Management Module Hardware VPD
      -- ********************************************************************************
      mmHardwareVpd OBJECT IDENTIFIER ::= { vpdInformation 2 }

      mmHardwareVpdTable OBJECT-TYPE
                    SYNTAX  SEQUENCE OF MmHardwareVpdEntry
                    ACCESS  not-accessible
                    STATUS  deprecated
                    DESCRIPTION
                    "Table of the management module hardware components.
                    For consistent results, view as a table and not as individual entries."
                    ::= { mmHardwareVpd 1 }

      mmHardwareVpdEntry OBJECT-TYPE
                    SYNTAX MmHardwareVpdEntry
                    ACCESS  not-accessible
                    STATUS  deprecated
                    DESCRIPTION
                    "Management module hardware VPD entry.
                    For consistent results, view as a table and not as individual entries."
                    INDEX { mmHardwareVpdIndex }
                    ::= { mmHardwareVpdTable 1 }

      MmHardwareVpdEntry ::= SEQUENCE {
                  mmHardwareVpdIndex INTEGER,
                  mmHardwareVpdBayNumber OCTET STRING,
                  mmHardwareVpdManufacturingId OCTET STRING,
                  mmHardwareVpdFruNumber OCTET STRING,
                  mmHardwareVpdHardwareRevision INTEGER,
                  mmHardwareVpdUuid OCTET STRING,
                  mmHardwareVpdManufDate OCTET STRING,
                  mmHardwareVpdPartNumber OCTET STRING,
                  mmHardwareVpdFruSerial OCTET STRING,
                  mmHardwareVpdManufacturingIDNumber OCTET STRING,
                  mmHardwareVpdProductId OCTET STRING,
                  mmHardwareVpdSubManufacturerId OCTET STRING,
                  mmHardwareVpdClei OCTET STRING,
                  mmHardwareVpdHardwareRevisionString OCTET STRING
                  }

      mmHardwareVpdIndex  OBJECT-TYPE
                  SYNTAX  INTEGER
                  ACCESS  read-only
                  STATUS  deprecated
                  DESCRIPTION
                  "Management module hardware VPD index.
                  For consistent results, view as a table and not as individual entries."
                  ::= { mmHardwareVpdEntry 1 }

      mmHardwareVpdBayNumber  OBJECT-TYPE
                  SYNTAX  OCTET STRING
                  ACCESS  read-only
                  STATUS  deprecated
                  DESCRIPTION
                  "Management module hardware VPD Bay number.
                  For consistent results, view as a table and not as individual entries."
                  ::= { mmHardwareVpdEntry 2 }

      mmHardwareVpdManufacturingId  OBJECT-TYPE
                  SYNTAX  OCTET STRING
                  ACCESS  read-only
                  STATUS  deprecated
                  DESCRIPTION
                  "Management module hardware VPD manufacturing ID.
                  For consistent results, view as a table and not as individual entries."
                  ::= { mmHardwareVpdEntry 3 }

      mmHardwareVpdFruNumber  OBJECT-TYPE
                  SYNTAX  OCTET STRING
                  ACCESS  read-only
                  STATUS  deprecated
                  DESCRIPTION
                  "Management module hardware VPD FRU number.
                  For consistent results, view as a table and not as individual entries."
                  ::= { mmHardwareVpdEntry 4 }



      mmHardwareVpdHardwareRevision  OBJECT-TYPE
                  SYNTAX  INTEGER
                  ACCESS  read-only
                  STATUS  deprecated
                  DESCRIPTION
                  "Management module hardware VPD hardware revision.
                  For consistent results, view as a table and not as individual entries.
                  If a hardware revision is programmed in the OEM VPD area for this component,
                  then the HardwareRevisionString version of this MIB object should be used."
                  ::= { mmHardwareVpdEntry 5 }

      mmHardwareVpdUuid  OBJECT-TYPE
                  SYNTAX  OCTET STRING
                  ACCESS  read-only
                  STATUS  deprecated
                  DESCRIPTION
                  "Management module hardware VPD UUID.
                  For consistent results, view as a table and not as individual entries."
                  ::= { mmHardwareVpdEntry 6 }


      mmHardwareVpdManufDate  OBJECT-TYPE
                  SYNTAX  OCTET STRING
                  ACCESS  read-only
                  STATUS  deprecated
                  DESCRIPTION
                  "Management module hardware VPD manufacture date.
                  For consistent results, view as a table and not as individual entries."
                  ::= { mmHardwareVpdEntry 7 }


      mmHardwareVpdPartNumber  OBJECT-TYPE
                  SYNTAX  OCTET STRING
                  ACCESS  read-only
                  STATUS  deprecated
                  DESCRIPTION
                  "Management module hardware VPD Part number.
                  For consistent results, view as a table and not as individual entries."
                  ::= { mmHardwareVpdEntry 8 }

      mmHardwareVpdFruSerial  OBJECT-TYPE
                  SYNTAX  OCTET STRING
                  ACCESS  read-only
                  STATUS  deprecated
                  DESCRIPTION
                  "Management module hardware VPD FRU serial number.
                  For consistent results, view as a table and not as individual entries."
                  ::= { mmHardwareVpdEntry 9 }

      mmHardwareVpdManufacturingIDNumber  OBJECT-TYPE
                  SYNTAX  OCTET STRING
                  ACCESS  read-only
                  STATUS  deprecated
                  DESCRIPTION
                  "Management module hardware VPD manufacturer ID Number.
                  For consistent results, view as a table and not as individual entries."
                  ::= { mmHardwareVpdEntry 10 }

      mmHardwareVpdProductId  OBJECT-TYPE
                  SYNTAX  OCTET STRING
                  ACCESS  read-only
                  STATUS  deprecated
                  DESCRIPTION
                  "Management module hardware VPD product ID.
                  For consistent results, view as a table and not as individual entries."
                  ::= { mmHardwareVpdEntry 11 }

      mmHardwareVpdSubManufacturerId  OBJECT-TYPE
                  SYNTAX  OCTET STRING
                  ACCESS  read-only
                  STATUS  deprecated
                  DESCRIPTION
                  "Management module hardware VPD subsystem manufacturer.
                  For consistent results, view as a table and not as individual entries."
                  ::= { mmHardwareVpdEntry 12 }

      mmHardwareVpdClei  OBJECT-TYPE
                  SYNTAX  OCTET STRING
                  ACCESS  read-only
                  STATUS  deprecated
                  DESCRIPTION
                  "Management module hardware VPD Common
                  Language Equipment Identification (CLEI).
                  For consistent results, view as a table and not as individual entries."
                  ::= { mmHardwareVpdEntry 13 }

      mmHardwareVpdHardwareRevisionString  OBJECT-TYPE
                  SYNTAX  OCTET STRING
                  ACCESS  read-only
                  STATUS  deprecated
                  DESCRIPTION
                  "Management module hardware VPD hardware revision in string format.
                  For consistent results, view as a table and not as individual entries.
                  If a hardware revision is programmed in the OEM VPD area for this component,
                  then this MIB object should be used."
                  ::= { mmHardwareVpdEntry 14 }

      -- ********************************************************************************
      -- System Firmware Level VPD
      -- ********************************************************************************
      mmFirmwareVpd OBJECT IDENTIFIER ::= { vpdInformation 3 }

       -- ********************************************************************************
       -- MM Firmware VPD
       -- ********************************************************************************
       mmMainApplVpdTable OBJECT-TYPE
                     SYNTAX  SEQUENCE OF MmMainApplVpdEntry
                     ACCESS  not-accessible
                     STATUS  deprecated
                     DESCRIPTION
                     "Table of MM Firmware VPD."
                     ::= { mmFirmwareVpd 1 }

       mmMainApplVpdEntry OBJECT-TYPE
                     SYNTAX MmMainApplVpdEntry
                     ACCESS  not-accessible
                     STATUS  deprecated
                     DESCRIPTION
                     "MM Firmware VPD entry."
                     INDEX { mmMainApplVpdIndex }
                     ::= { mmMainApplVpdTable 1 }


       MmMainApplVpdEntry ::= SEQUENCE {
                   mmMainApplVpdIndex INTEGER,
                   mmMainApplVpdName OCTET STRING,
                   mmMainApplVpdBuildId OCTET STRING,
                   mmMainApplVpdRevisonNumber OCTET STRING,
                   mmMainApplVpdFilename OCTET STRING,
                   mmMainApplVpdBuildDate OCTET STRING
                   }

       mmMainApplVpdIndex  OBJECT-TYPE
                   SYNTAX  INTEGER
                   ACCESS  read-only
                   STATUS  deprecated
                   DESCRIPTION
                   "Firmware VPD index."
                   ::= { mmMainApplVpdEntry 1 }

       mmMainApplVpdName  OBJECT-TYPE
                   SYNTAX  OCTET STRING
                   ACCESS  read-only
                   STATUS  deprecated
                   DESCRIPTION
                   "Firmware VPD name description.
                   'MM firmware' indicates the running firmware of the MM.
                   'MM firmware (pending restart)' indicates the flashed
                   firmware of the MM which will become active after the
                   next restart."
                   ::= { mmMainApplVpdEntry 2 }

       mmMainApplVpdBuildId  OBJECT-TYPE
                   SYNTAX  OCTET STRING
                   ACCESS  read-only
                   STATUS  deprecated
                   DESCRIPTION
                   "Firmware VPD build identification."
                   ::= { mmMainApplVpdEntry 3 }

       mmMainApplVpdRevisonNumber  OBJECT-TYPE
                   SYNTAX  OCTET STRING
                   ACCESS  read-only
                   STATUS  deprecated
                   DESCRIPTION
                   "Firmware VPD revision number."
                   ::= { mmMainApplVpdEntry 4 }

       mmMainApplVpdFilename  OBJECT-TYPE
                   SYNTAX  OCTET STRING
                   ACCESS  read-only
                   STATUS  deprecated
                   DESCRIPTION
                   "Firmware VPD file name."
                   ::= { mmMainApplVpdEntry 5 }

       mmMainApplVpdBuildDate  OBJECT-TYPE
                   SYNTAX  OCTET STRING
                   ACCESS  read-only
                   STATUS  deprecated
                   DESCRIPTION
                   "Firmware VPD build date."
                   ::= { mmMainApplVpdEntry 6 }

      -- ********************************************************************************
      -- System Component Level VPD Activity log
      -- ********************************************************************************
      inventoryManagementActivityVpdTable OBJECT-TYPE
                    SYNTAX  SEQUENCE OF InventoryManagementActivityVpdEntry
                    ACCESS  not-accessible
                    STATUS  mandatory
                    DESCRIPTION
                    "Table of system component hardware VPD activity log.
                    For consistent results, view as a table and not as individual entries."
                    ::= { vpdInformation 22 }

      inventoryManagementActivityVpdEntry OBJECT-TYPE
                    SYNTAX InventoryManagementActivityVpdEntry
                    ACCESS  not-accessible
                    STATUS  mandatory
                    DESCRIPTION
                    "System component hardware VPD activity log entry.
                    For consistent results, view as a table and not as individual entries."
                    INDEX { componentLevelActivityVpdIndex }
                    ::= { inventoryManagementActivityVpdTable 1 }

      InventoryManagementActivityVpdEntry ::= SEQUENCE {
                  componentLevelActivityVpdIndex INTEGER,
                  componentLevelActivityVpdFruNumber OCTET STRING,
                  componentLevelActivityVpdSerialNumber OCTET STRING,
                  componentLevelActivityVpdManufacturingId OCTET STRING,
                  componentLevelActivityVpdBayNumber OCTET STRING, 
                  componentLevelActivityVpdAction OCTET STRING,
                  componentLevelActivityVpdTimestamp OCTET STRING,
                  componentLevelActivityVpdModuleName OCTET STRING,
                  componentLevelActivityVpdTopologyPath OCTET STRING
                  }

      componentLevelActivityVpdIndex  OBJECT-TYPE
                  SYNTAX  INTEGER
                  ACCESS  read-only
                  STATUS  mandatory
                  DESCRIPTION
                  "System component level VPD activity log index.
                  For consistent results, view as a table and not as individual entries."
                  ::= { inventoryManagementActivityVpdEntry 1 }

      componentLevelActivityVpdFruNumber  OBJECT-TYPE
                  SYNTAX  OCTET STRING
                  ACCESS  read-only
                  STATUS  mandatory
                  DESCRIPTION
                  "System component level VPD activity log FRU number.
                  For consistent results, view as a table and not as individual entries."
                  ::= { inventoryManagementActivityVpdEntry 2 }

      componentLevelActivityVpdSerialNumber  OBJECT-TYPE
                  SYNTAX  OCTET STRING
                  ACCESS  read-only
                  STATUS  mandatory
                  DESCRIPTION
                  "System component level VPD activity log serial number.
                  For consistent results, view as a table and not as individual entries."
                  ::= { inventoryManagementActivityVpdEntry 3 }

      componentLevelActivityVpdManufacturingId  OBJECT-TYPE
                  SYNTAX  OCTET STRING
                  ACCESS  read-only
                  STATUS  mandatory
                  DESCRIPTION
                  "System component level VPD activity log manufacturing ID.
                  For consistent results, view as a table and not as individual entries."
                  ::= { inventoryManagementActivityVpdEntry 4 }

      componentLevelActivityVpdBayNumber  OBJECT-TYPE
                  SYNTAX  OCTET STRING
                  ACCESS  read-only
                  STATUS  deprecated
                  DESCRIPTION
                  "System component level VPD activity log Bay number.
                  For consistent results, view as a table and not as individual entries."
                  ::= { inventoryManagementActivityVpdEntry 5 }

      componentLevelActivityVpdAction  OBJECT-TYPE
                  SYNTAX  OCTET STRING
                  ACCESS  read-only
                  STATUS  mandatory
                  DESCRIPTION
                  "System component level VPD activity log action (added/removed).
                  For consistent results, view as a table and not as individual entries."
                  ::= {inventoryManagementActivityVpdEntry 9 }

      componentLevelActivityVpdTimestamp  OBJECT-TYPE
                  SYNTAX  OCTET STRING
                  ACCESS  read-only
                  STATUS  mandatory
                  DESCRIPTION
                  "System component level VPD activity log timestamp.
                  For consistent results, view as a table and not as individual entries."
                  ::= { inventoryManagementActivityVpdEntry 10 }

      componentLevelActivityVpdModuleName  OBJECT-TYPE
                  SYNTAX  OCTET STRING
                  ACCESS  read-only
                  STATUS  mandatory
                  DESCRIPTION
                  "The module name which this row is associated with.
                  For consistent results, view as a table and not as individual entries."
                  ::= { inventoryManagementActivityVpdEntry 12 }

      componentLevelActivityVpdTopologyPath  OBJECT-TYPE
                  SYNTAX  OCTET STRING  (SIZE (0..100))
                  ACCESS  read-only
                  STATUS  mandatory
                  DESCRIPTION
                  "The chassis and each installed component is represented by a hardware 
                   topology tree, where each node in the tree represents a component. 

                   As an example, the root of the tree is the chassis and is represented
                   by the pair 'CHASSIS, 1'. This pair indicates the first instance of
                   the chassis. If a blade is inserted in slot 4 of the chassis, its
                   topology path is 'CHASSIS, 1, BLADE, 4'. With this format, the
                   components in the chassis can be determined along with their relative
                   hierarchy to each other.

                   The topology path's numeric designations for the components are:

                    CHASSIS,                0x01   Chassis
                    MM,                     0x02   Management Module
                    BLADE,                  0x03   Main system board of a blade
                    POWER,                  0x04   Power Supply, Power Module, etc
                    COOLING,                0x05   Fan, blower, or other cooling device
                    IO_MODULE,              0x06   Has I/O interface, i.e. - switch or bridge
                    MEDIA,                  0x07   Media device
                    PROCESSOR,              0x08   Any processor, processor module, etc
                    STORAGE,                0x09   Any type of storage device
                    EXPANSION,              0x0A   Expansion Card (not covered by more specific type)
                    MEMORY,                 0x0B   Any memory device, module, etc
                    MFRU,                   0x0C   Managed FRU Device
                    PANEL,                  0x0D   Any sort of panel device, such as a front panel
                    BLADE_EXPANSION_MODULE, 0x0E   Expansion option (BEM) such as PEU, BSE, etc
                    CARD_EXPANSION,         0x0F   Expansion card, ie. daughter card
                    CARD_HS_EXPANSION,      0x10   High Speed Expansion card, ie. daughter card
                    INTERPOSER,             0x11   Interposer device
                    CLOCK,                  0x12   Clock card
                    MUX,                    0x13   Mulitplexer card
                    ADDIN,                  0x14   cKVM card & other addin cards
                    STORAGE_MODULE,         0x15   Container of one or more Storage Devices
                    SYS_EXPANSION_CARD,     0x16   Management card
                    BATTERY,                0x17   A single battery
                    BATTERY_MODULE,         0x18   Container of one or more batteries
                    REAR_LED,               0x19   Rear LED card
                    MEMORY_BANK,            0x1A   Memory banks
                    AIR_FILTER,             0x1B   Filter mechanism (bezel)
                    SERIAL_PORT_MODULE,     0x1C   Container of one or more serial ports
                    PARENT,                 0x1D   Reference to parent for multi-parent support
                    PHY_PORT,               0x1E   Physical port
                    IO_EXPANDER,            0x1F   RAID card
                    CABLE,                  0x20   Cable/Interconnect
                    FAN_MUX,                0x29   Fan multiplexer card
                     PCI_EXPRESS,            0x32   PCI express card on (PEN)
                     FLASH_DIMM,             0x33   Used for SPD devices that matches the silkscreen of the DIMM slot
                     RACK,                   0x50   Rack
                     PLATFORM,               0x51   Generic Platform like rack mounted server/appliance
                     DATAPLEX,               0x52   DataPlex
                     OTHER,                  0x53   Other unknown etc.
                     PERIPHERAL_MODULE,      0x54 
                     SYSTEM_BOARD,           0x55   System board
                     PROCESSOR_MODULE,       0x56 
                     BACK_PANEL,             0x57 
                     POWER_SYSTEM_BOARD,     0x58 
                     STORAGE_BACKPLANE,      0x59   Drive back plane
                     PROC_BOARD,             0x5A   Holds 1 or more processors
                     POWER_DI,               0x5B   Power mgt / power distribution board
                     CHASSIS_BACK_PANEL,     0x5C 
                     SUB_CHASSIS,            0x5D 
                     OTHER_CHASSIS_BOARD,    0x5E 
                     DEVICE_MODULE,          0x5F 
                     REMOTE_DEVICE,          0x60   Remote mgt communication device
                     EXTERNAL_ENVIRONMENT,   0x61   Such as external temp sensor for outside box temps
                     PROC_MEMORY_MODULE,     0x62   Processors and memory on same module"

                  ::= { inventoryManagementActivityVpdEntry  15 }


      -- ********************************************************************************
      -- Blade Hardware VPD
      -- ********************************************************************************
      bladeHardwareVpd OBJECT IDENTIFIER ::= { vpdInformation 4 }

      bladeHardwareVpdTable OBJECT-TYPE
                    SYNTAX  SEQUENCE OF BladeHardwareVpdEntry
                    ACCESS  not-accessible
                    STATUS  deprecated
                    DESCRIPTION
                    "Table of VPD information for the blade hardware components.
                    For consistent results, view as a table and not as individual entries."
                    ::= { bladeHardwareVpd 1 }

      bladeHardwareVpdEntry OBJECT-TYPE
                    SYNTAX BladeHardwareVpdEntry
                    ACCESS  not-accessible
                    STATUS  deprecated
                    DESCRIPTION
                    "Blade hardware VPD entry.
                    For consistent results, view as a table and not as individual entries."
                    INDEX { bladeHardwareVpdIndex }
                    ::= { bladeHardwareVpdTable 1 }

      BladeHardwareVpdEntry ::= SEQUENCE {
                  bladeHardwareVpdIndex INTEGER,
                  bladeHardwareVpdBayNumber OCTET STRING,
                  bladeHardwareVpdManufacturingId OCTET STRING,
                  bladeHardwareVpdFruNumber OCTET STRING,
                  bladeHardwareVpdHardwareRevision INTEGER,
                  bladeHardwareVpdSerialNumber OCTET STRING,
                  bladeHardwareVpdMachineType OCTET STRING,
                  bladeHardwareVpdUuid OCTET STRING,
                  bladeHardwareVpdManufDate OCTET STRING,
                  bladeHardwareVpdPartNumber OCTET STRING,
                  bladeHardwareVpdFruSerial OCTET STRING,
                  bladeHardwareVpdMachineModel OCTET STRING,
                  bladeHardwareVpdManufacturingIDNumber OCTET STRING,
                  bladeHardwareVpdProductId OCTET STRING,
                  bladeHardwareVpdSubManufacturerId OCTET STRING,
                  bladeHardwareVpdClei OCTET STRING,
                  bladeHardwareVpdHardwareRevisionString OCTET STRING,
                  bladeDaughterVpdCardType INTEGER,
                  bladeDaughterVpdManufacturingId OCTET STRING,
                  bladeDaughterVpdFruNumber OCTET STRING,
                  bladeDaughterVpdHardwareRevision INTEGER,
                  bladeDaughterVpdSerialNumber OCTET STRING,
                  bladeDaughterVpdMachineType OCTET STRING,
                  bladeDaughterVpdUuid OCTET STRING,
                  bladeDaughterVpdManufDate OCTET STRING,
                  bladeDaughterVpdPartNumber OCTET STRING,
                  bladeDaughterVpdFruSerial OCTET STRING,
                  bladeDaughterVpdManufacturingIDNumber OCTET STRING,
                  bladeDaughterVpdProductId OCTET STRING,
                  bladeDaughterVpdSubManufacturerId OCTET STRING,
                  bladeDaughterVpdClei OCTET STRING,
                  bladeDaughterVpdHardwareRevisionString OCTET STRING
                  }

      bladeHardwareVpdIndex  OBJECT-TYPE
                  SYNTAX  INTEGER
                  ACCESS  read-only
                  STATUS  deprecated
                  DESCRIPTION
                  "Blade hardware VPD index.
                  For consistent results, view as a table and not as individual entries."
                  ::= { bladeHardwareVpdEntry 1 }

      bladeHardwareVpdBayNumber  OBJECT-TYPE
                  SYNTAX  OCTET STRING
                  ACCESS  read-only
                  STATUS  deprecated
                  DESCRIPTION
                  "Blade hardware VPD Bay number.
                  For consistent results, view as a table and not as individual entries."
                  ::= { bladeHardwareVpdEntry 2 }

      bladeHardwareVpdManufacturingId  OBJECT-TYPE
                  SYNTAX  OCTET STRING
                  ACCESS  read-only
                  STATUS  deprecated
                  DESCRIPTION
                  "Blade hardware VPD manufacturing ID.
                  For consistent results, view as a table and not as individual entries."
                  ::= { bladeHardwareVpdEntry 3 }

      bladeHardwareVpdFruNumber  OBJECT-TYPE
                  SYNTAX  OCTET STRING
                  ACCESS  read-only
                  STATUS  deprecated
                  DESCRIPTION
                  "Blade hardware VPD FRU number.
                  For consistent results, view as a table and not as individual entries."
                  ::= { bladeHardwareVpdEntry 4 }

      bladeHardwareVpdHardwareRevision  OBJECT-TYPE
                  SYNTAX  INTEGER
                  ACCESS  read-only
                  STATUS  deprecated
                  DESCRIPTION
                  "Blade hardware VPD hardware revision.
                  For consistent results, view as a table and not as individual entries.
                  If a hardware revision is programmed in the OEM VPD area for this component,
                  then the HardwareRevisionString version of this MIB object should be used."
                  ::= { bladeHardwareVpdEntry 5 }

      bladeHardwareVpdSerialNumber  OBJECT-TYPE
                  SYNTAX  OCTET STRING
                  ACCESS  read-only
                  STATUS  deprecated
                  DESCRIPTION
                  "Blade hardware VPD serial number.
                  For consistent results, view as a table and not as individual entries."
                  ::= { bladeHardwareVpdEntry 6 }

      bladeHardwareVpdMachineType  OBJECT-TYPE
                  SYNTAX  OCTET STRING
                  ACCESS  read-only
                  STATUS  deprecated
                  DESCRIPTION
                  "Blade hardware VPD machine type.
                  For consistent results, view as a table and not as individual entries."
                  ::= { bladeHardwareVpdEntry 7 }

      bladeHardwareVpdUuid  OBJECT-TYPE
                  SYNTAX  OCTET STRING
                  ACCESS  read-only
                  STATUS  deprecated
                  DESCRIPTION
                  "Blade hardware VPD UUID.
                  For consistent results, view as a table and not as individual entries."
                  ::= { bladeHardwareVpdEntry 8 }

      bladeHardwareVpdManufDate  OBJECT-TYPE
                  SYNTAX  OCTET STRING
                  ACCESS  read-only
                  STATUS  deprecated
                  DESCRIPTION
                  "Blade hardware VPD Manufacture Date.
                  For consistent results, view as a table and not as individual entries."
                  ::= { bladeHardwareVpdEntry 9 }

      bladeHardwareVpdPartNumber  OBJECT-TYPE
                  SYNTAX  OCTET STRING
                  ACCESS  read-only
                  STATUS  deprecated
                  DESCRIPTION
                  "Blade hardware VPD Part number.
                  For consistent results, view as a table and not as individual entries."
                  ::= { bladeHardwareVpdEntry 10 }

      bladeHardwareVpdFruSerial  OBJECT-TYPE
                  SYNTAX  OCTET STRING
                  ACCESS  read-only
                  STATUS  deprecated
                  DESCRIPTION
                  "Blade hardware VPD FRU serial number.
                  For consistent results, view as a table and not as individual entries."
                  ::= { bladeHardwareVpdEntry 11 }

      bladeHardwareVpdMachineModel  OBJECT-TYPE
                  SYNTAX  OCTET STRING
                  ACCESS  read-only
                  STATUS  deprecated
                  DESCRIPTION
                  "Blade hardware VPD machine model.
                  For consistent results, view as a table and not as individual entries."
                  ::= { bladeHardwareVpdEntry 12 }

      bladeHardwareVpdManufacturingIDNumber  OBJECT-TYPE
                  SYNTAX  OCTET STRING
                  ACCESS  read-only
                  STATUS  deprecated
                  DESCRIPTION
                  "Blade hardware VPD Manufacturer ID Number.
                  For consistent results, view as a table and not as individual entries."
                  ::= { bladeHardwareVpdEntry 13 }

      bladeHardwareVpdProductId  OBJECT-TYPE
                  SYNTAX  OCTET STRING
                  ACCESS  read-only
                  STATUS  deprecated
                  DESCRIPTION
                  "Blade hardware VPD product ID.
                  For consistent results, view as a table and not as individual entries."
                  ::= { bladeHardwareVpdEntry 14 }

      bladeHardwareVpdSubManufacturerId  OBJECT-TYPE
                  SYNTAX  OCTET STRING
                  ACCESS  read-only
                  STATUS  deprecated
                  DESCRIPTION
                  "Blade hardware VPD subsystem manufacturer ID.
                  For consistent results, view as a table and not as individual entries."
                  ::= { bladeHardwareVpdEntry 15 }

      bladeHardwareVpdClei  OBJECT-TYPE
                  SYNTAX  OCTET STRING
                  ACCESS  read-only
                  STATUS  deprecated
                  DESCRIPTION
                  "Blade hardware VPD Common Language Equipment Identifier (CLEI).
                  For consistent results, view as a table and not as individual entries."
                  ::= { bladeHardwareVpdEntry 16 }

      bladeHardwareVpdHardwareRevisionString  OBJECT-TYPE
                  SYNTAX  OCTET STRING
                  ACCESS  read-only
                  STATUS  deprecated
                  DESCRIPTION
                  "Blade hardware VPD hardware revision in string format.
                  For consistent results, view as a table and not as individual entries.
                  If a hardware revision is programmed in the OEM VPD area for this component,
                  then this MIB object should be used."
                  ::= { bladeHardwareVpdEntry 17 }

      bladeDaughterVpdCardType  OBJECT-TYPE
                  SYNTAX  INTEGER  {
                    unknown(0),
                    networkExpansion(1),
                    storageExpansion(2),
                    pciExpansion(3),
                    genericExpansion(4)
                  }
                  ACCESS  read-only
                  STATUS  deprecated
                  DESCRIPTION
                  "Blade expansion card (daughter card) VPD type.
                  For consistent results, view as a table and not as individual entries."
                  ::= { bladeHardwareVpdEntry 20 }

      bladeDaughterVpdManufacturingId  OBJECT-TYPE
                  SYNTAX  OCTET STRING
                  ACCESS  read-only
                  STATUS  deprecated
                  DESCRIPTION
                  "Blade expansion card (daughter card) VPD manufacturing ID.
                  For consistent results, view as a table and not as individual entries."
                  ::= { bladeHardwareVpdEntry 21 }

      bladeDaughterVpdFruNumber  OBJECT-TYPE
                  SYNTAX  OCTET STRING
                  ACCESS  read-only
                  STATUS  deprecated
                  DESCRIPTION
                  "Blade expansion card (daughter card) VPD FRU number.
                  For consistent results, view as a table and not as individual entries."
                  ::= { bladeHardwareVpdEntry 22 }

      bladeDaughterVpdHardwareRevision  OBJECT-TYPE
                  SYNTAX  INTEGER
                  ACCESS  read-only
                  STATUS  deprecated
                  DESCRIPTION
                  "Blade expansion card (daughter card) VPD hardware revision.
                  For consistent results, view as a table and not as individual entries.
                  If a hardware revision is programmed in the OEM VPD area for this component,
                  then the HardwareRevisionString version of this MIB object should be used."
                  ::= { bladeHardwareVpdEntry 23 }

      bladeDaughterVpdSerialNumber  OBJECT-TYPE
                  SYNTAX  OCTET STRING
                  ACCESS  read-only
                  STATUS  deprecated
                  DESCRIPTION
                  "Blade expansion card (daughter card) VPD Serial number.
                  For consistent results, view as a table and not as individual entries."
                  ::= { bladeHardwareVpdEntry 24 }

      bladeDaughterVpdMachineType  OBJECT-TYPE
                  SYNTAX  OCTET STRING
                  ACCESS  read-only
                  STATUS  deprecated
                  DESCRIPTION
                  "Blade expansion card (daughter card) VPD Machine type.
                  For consistent results, view as a table and not as individual entries."
                  ::= { bladeHardwareVpdEntry 25 }

      bladeDaughterVpdUuid  OBJECT-TYPE
                  SYNTAX  OCTET STRING
                  ACCESS  read-only
                  STATUS  deprecated
                  DESCRIPTION
                  "Blade expansion card (daughter card) VPD UUID.
                  For consistent results, view as a table and not as individual entries."
                  ::= { bladeHardwareVpdEntry 26 }

      bladeDaughterVpdManufDate  OBJECT-TYPE
                  SYNTAX  OCTET STRING
                  ACCESS  read-only
                  STATUS  deprecated
                  DESCRIPTION
                  "Blade expansion card (daughter card) VPD Manufacture date.
                  For consistent results, view as a table and not as individual entries."
                  ::= { bladeHardwareVpdEntry 27 }

      bladeDaughterVpdPartNumber  OBJECT-TYPE
                  SYNTAX  OCTET STRING
                  ACCESS  read-only
                  STATUS  deprecated
                  DESCRIPTION
                  "Blade expansion card (daughter card) VPD Part number.
                  For consistent results, view as a table and not as individual entries."
                  ::= { bladeHardwareVpdEntry 28 }

      bladeDaughterVpdFruSerial  OBJECT-TYPE
                  SYNTAX  OCTET STRING
                  ACCESS  read-only
                  STATUS  deprecated
                  DESCRIPTION
                  "Blade expansion card (daughter card) VPD FRU Serial.
                  For consistent results, view as a table and not as individual entries."
                  ::= { bladeHardwareVpdEntry 29 }

      bladeDaughterVpdManufacturingIDNumber  OBJECT-TYPE
                  SYNTAX  OCTET STRING
                  ACCESS  read-only
                  STATUS  deprecated
                  DESCRIPTION
                  "Blade expansion card (daughter card) VPD manufacturer ID Number.
                  For consistent results, view as a table and not as individual entries."
                  ::= { bladeHardwareVpdEntry 30 }

      bladeDaughterVpdProductId  OBJECT-TYPE
                  SYNTAX  OCTET STRING
                  ACCESS  read-only
                  STATUS  deprecated
                  DESCRIPTION
                  "Blade expansion card (daughter card) VPD product ID.
                  For consistent results, view as a table and not as individual entries."
                  ::= { bladeHardwareVpdEntry 31 }

      bladeDaughterVpdSubManufacturerId  OBJECT-TYPE
                  SYNTAX  OCTET STRING
                  ACCESS  read-only
                  STATUS  deprecated
                  DESCRIPTION
                  "Blade expansion card (daughter card) VPD subsystem manufacturing ID.
                  For consistent results, view as a table and not as individual entries."
                  ::= { bladeHardwareVpdEntry 32 }

      bladeDaughterVpdClei  OBJECT-TYPE
                  SYNTAX  OCTET STRING
                  ACCESS  read-only
                  STATUS  deprecated
                  DESCRIPTION
                  "Blade expansion card (daughter card) VPD
                  Common Language Equipment Identifier (CLEI).
                  For consistent results, view as a table and not as individual entries."
                  ::= { bladeHardwareVpdEntry 33 }

      bladeDaughterVpdHardwareRevisionString  OBJECT-TYPE
                  SYNTAX  OCTET STRING
                  ACCESS  read-only
                  STATUS  deprecated
                  DESCRIPTION
                  "Blade expansion card (daughter card) VPD hardware revision in string format.
                  For consistent results, view as a table and not as individual entries.
                  If a hardware revision is programmed in the OEM VPD area for this component,
                  then this MIB object should be used."
                  ::= { bladeHardwareVpdEntry 34 }

      -- ********************************************************************************
      -- Blade MAC Address VPD
      -- ********************************************************************************

      bladeMACAddressVpdTable OBJECT-TYPE
                    SYNTAX  SEQUENCE OF BladeMACAddressVpdEntry
                    ACCESS  not-accessible
                    STATUS  mandatory
                    DESCRIPTION
                    "Table of MAC addresses of the blade and its expansion cards (daughter cards).
                    For consistent results, view as a table and not as individual entries."
                    ::= { bladeHardwareVpd 2 }

      bladeMACAddressVpdEntry OBJECT-TYPE
                    SYNTAX BladeMACAddressVpdEntry
                    ACCESS  not-accessible
                    STATUS  mandatory
                    DESCRIPTION
                    "Blade MAC address entry.
                    For consistent results, view as a table and not as individual entries."
                    INDEX { bladeMACAddressVpdIndex }
                    ::= { bladeMACAddressVpdTable 1 }

      BladeMACAddressVpdEntry ::= SEQUENCE {
                  bladeMACAddressVpdIndex INTEGER,
                  bladeMACAddress1Vpd              OCTET STRING,
                  bladeMACAddress2Vpd              OCTET STRING,
                  bladeMACAddress3Vpd              OCTET STRING,
                  bladeMACAddress4Vpd              OCTET STRING,
                  bladeMACAddress5Vpd              OCTET STRING,
                  bladeMACAddress6Vpd              OCTET STRING,
                  bladeMACAddress7Vpd              OCTET STRING,
                  bladeMACAddress8Vpd              OCTET STRING,
                  bladeDaughterCard1MACAddress1Vpd OCTET STRING,
                  bladeDaughterCard1MACAddress2Vpd OCTET STRING,
                  bladeDaughterCard1MACAddress3Vpd OCTET STRING,
                  bladeDaughterCard1MACAddress4Vpd OCTET STRING,
                  bladeDaughterCard1MACAddress5Vpd OCTET STRING,
                  bladeDaughterCard1MACAddress6Vpd OCTET STRING,
                  bladeDaughterCard1MACAddress7Vpd OCTET STRING,
                  bladeDaughterCard1MACAddress8Vpd OCTET STRING,
                  bladeDaughterCard2MACAddress1Vpd OCTET STRING,
                  bladeDaughterCard2MACAddress2Vpd OCTET STRING,
                  bladeDaughterCard2MACAddress3Vpd OCTET STRING,
                  bladeDaughterCard2MACAddress4Vpd OCTET STRING,
                  bladeDaughterCard2MACAddress5Vpd OCTET STRING,
                  bladeDaughterCard2MACAddress6Vpd OCTET STRING,
                  bladeDaughterCard2MACAddress7Vpd OCTET STRING,
                  bladeDaughterCard2MACAddress8Vpd OCTET STRING,
                  bladeDaughterCard3MACAddress1Vpd OCTET STRING,
                  bladeDaughterCard3MACAddress2Vpd OCTET STRING,
                  bladeDaughterCard3MACAddress3Vpd OCTET STRING,
                  bladeDaughterCard3MACAddress4Vpd OCTET STRING,
                  bladeDaughterCard3MACAddress5Vpd OCTET STRING,
                  bladeDaughterCard3MACAddress6Vpd OCTET STRING,
                  bladeDaughterCard3MACAddress7Vpd OCTET STRING,
                  bladeDaughterCard3MACAddress8Vpd OCTET STRING,
                  bladeDaughterCard4MACAddress1Vpd OCTET STRING,
                  bladeDaughterCard4MACAddress2Vpd OCTET STRING,
                  bladeDaughterCard4MACAddress3Vpd OCTET STRING,
                  bladeDaughterCard4MACAddress4Vpd OCTET STRING,
                  bladeDaughterCard4MACAddress5Vpd OCTET STRING,
                  bladeDaughterCard4MACAddress6Vpd OCTET STRING,
                  bladeDaughterCard4MACAddress7Vpd OCTET STRING,
                  bladeDaughterCard4MACAddress8Vpd OCTET STRING,
                  bladeDaughterCard5MACAddress1Vpd OCTET STRING,
                  bladeDaughterCard5MACAddress2Vpd OCTET STRING,
                  bladeDaughterCard5MACAddress3Vpd OCTET STRING,
                  bladeDaughterCard5MACAddress4Vpd OCTET STRING,
                  bladeDaughterCard5MACAddress5Vpd OCTET STRING,
                  bladeDaughterCard5MACAddress6Vpd OCTET STRING,
                  bladeDaughterCard5MACAddress7Vpd OCTET STRING,
                  bladeDaughterCard5MACAddress8Vpd OCTET STRING,
                  bladeHSDaughterCard1MACAddress1Vpd OCTET STRING,
                  bladeHSDaughterCard1MACAddress2Vpd OCTET STRING,
                  bladeHSDaughterCard1MACAddress3Vpd OCTET STRING,
                  bladeHSDaughterCard1MACAddress4Vpd OCTET STRING,
                  bladeHSDaughterCard1MACAddress5Vpd OCTET STRING,
                  bladeHSDaughterCard1MACAddress6Vpd OCTET STRING,
                  bladeHSDaughterCard1MACAddress7Vpd OCTET STRING,
                  bladeHSDaughterCard1MACAddress8Vpd OCTET STRING,
                  bladeSideCardMACAddress1Vpd      OCTET STRING,
                  bladeSideCardMACAddress2Vpd      OCTET STRING,
                  bladeSideCardMACAddress3Vpd      OCTET STRING,
                  bladeSideCardMACAddress4Vpd      OCTET STRING,
                  bladeSideCardMACAddress5Vpd      OCTET STRING,
                  bladeSideCardMACAddress6Vpd      OCTET STRING,
                  bladeSideCardMACAddress7Vpd      OCTET STRING,
                  bladeSideCardMACAddress8Vpd      OCTET STRING
                  }

      bladeMACAddressVpdIndex  OBJECT-TYPE
                  SYNTAX  INTEGER
                  ACCESS  read-only
                  STATUS  mandatory
                  DESCRIPTION
                  "Blade index.
                   For consistent results, view as a table and not as individual entries."
                  ::= { bladeMACAddressVpdEntry 1 }

      bladeMACAddress1Vpd  OBJECT-TYPE
                  SYNTAX  OCTET STRING
                  ACCESS  read-only
                  STATUS  mandatory
                  DESCRIPTION
                  "Blade MAC address 1.
                  For consistent results, view as a table and not as individual entries."
                  ::= { bladeMACAddressVpdEntry 2 }

      bladeMACAddress2Vpd  OBJECT-TYPE
                  SYNTAX  OCTET STRING
                  ACCESS  read-only
                  STATUS  mandatory
                  DESCRIPTION
                  "Blade MAC address 2.
                  For consistent results, view as a table and not as individual entries."
                  ::= { bladeMACAddressVpdEntry 3 }

      bladeMACAddress3Vpd  OBJECT-TYPE
                  SYNTAX  OCTET STRING
                  ACCESS  read-only
                  STATUS  mandatory
                  DESCRIPTION
                  "Blade MAC address 3.
                  For consistent results, view as a table and not as individual entries."
                  ::= { bladeMACAddressVpdEntry 4 }

      bladeMACAddress4Vpd  OBJECT-TYPE
                  SYNTAX  OCTET STRING
                  ACCESS  read-only
                  STATUS  mandatory
                  DESCRIPTION
                  "Blade MAC address 4.
                  For consistent results, view as a table and not as individual entries."
                  ::= { bladeMACAddressVpdEntry 5 }

      bladeMACAddress5Vpd  OBJECT-TYPE
                  SYNTAX  OCTET STRING
                  ACCESS  read-only
                  STATUS  mandatory
                  DESCRIPTION
                  "Blade MAC address 5.
                  For consistent results, view as a table and not as individual entries."
                  ::= { bladeMACAddressVpdEntry 6 }

      bladeMACAddress6Vpd  OBJECT-TYPE
                  SYNTAX  OCTET STRING
                  ACCESS  read-only
                  STATUS  mandatory
                  DESCRIPTION
                  "Blade MAC address 6.
                  For consistent results, view as a table and not as individual entries."
                  ::= { bladeMACAddressVpdEntry 7 }

      bladeMACAddress7Vpd  OBJECT-TYPE
                  SYNTAX  OCTET STRING
                  ACCESS  read-only
                  STATUS  mandatory
                  DESCRIPTION
                  "Blade MAC address 7.
                  For consistent results, view as a table and not as individual entries."
                  ::= { bladeMACAddressVpdEntry 8 }

      bladeMACAddress8Vpd  OBJECT-TYPE
                  SYNTAX  OCTET STRING
                  ACCESS  read-only
                  STATUS  mandatory
                  DESCRIPTION
                  "Blade MAC address 8.
                  For consistent results, view as a table and not as individual entries."
                  ::= { bladeMACAddressVpdEntry 9 }

      bladeDaughterCard1MACAddress1Vpd  OBJECT-TYPE
                  SYNTAX  OCTET STRING
                  ACCESS  read-only
                  STATUS  mandatory
                  DESCRIPTION
                  "Blade expansion card (daughter card) 1 MAC address 1.
                  For consistent results, view as a table and not as individual entries."
                  ::= { bladeMACAddressVpdEntry 10 }

      bladeDaughterCard1MACAddress2Vpd  OBJECT-TYPE
                  SYNTAX  OCTET STRING
                  ACCESS  read-only
                  STATUS  mandatory
                  DESCRIPTION
                  "Blade expansion card (daughter card) 1 MAC address 2.
                  For consistent results, view as a table and not as individual entries."
                  ::= { bladeMACAddressVpdEntry 11 }

      bladeDaughterCard1MACAddress3Vpd  OBJECT-TYPE
                  SYNTAX  OCTET STRING
                  ACCESS  read-only
                  STATUS  mandatory
                  DESCRIPTION
                  "Blade expansion card (daughter card) 1 MAC address 3.
                  For consistent results, view as a table and not as individual entries."
                  ::= { bladeMACAddressVpdEntry 12 }

      bladeDaughterCard1MACAddress4Vpd  OBJECT-TYPE
                  SYNTAX  OCTET STRING
                  ACCESS  read-only
                  STATUS  mandatory
                  DESCRIPTION
                  "Blade expansion card (daughter card) 1 MAC address 4.
                  For consistent results, view as a table and not as individual entries."
                  ::= { bladeMACAddressVpdEntry 13 }

      bladeDaughterCard1MACAddress5Vpd  OBJECT-TYPE
                  SYNTAX  OCTET STRING
                  ACCESS  read-only
                  STATUS  mandatory
                  DESCRIPTION
                  "Blade expansion card (daughter card) 1 MAC address 5.
                  For consistent results, view as a table and not as individual entries."
                  ::= { bladeMACAddressVpdEntry 14 }

      bladeDaughterCard1MACAddress6Vpd  OBJECT-TYPE
                  SYNTAX  OCTET STRING
                  ACCESS  read-only
                  STATUS  mandatory
                  DESCRIPTION
                  "Blade expansion card (daughter card) 1 MAC address 6.
                  For consistent results, view as a table and not as individual entries."
                  ::= { bladeMACAddressVpdEntry 15 }

      bladeDaughterCard1MACAddress7Vpd  OBJECT-TYPE
                  SYNTAX  OCTET STRING
                  ACCESS  read-only
                  STATUS  mandatory
                  DESCRIPTION
                  "Blade expansion card (daughter card) 1 MAC address 7.
                  For consistent results, view as a table and not as individual entries."
                  ::= { bladeMACAddressVpdEntry 16 }

      bladeDaughterCard1MACAddress8Vpd  OBJECT-TYPE
                  SYNTAX  OCTET STRING
                  ACCESS  read-only
                  STATUS  mandatory
                  DESCRIPTION
                  "Blade expansion card (daughter card) 1 MAC address 8.
                  For consistent results, view as a table and not as individual entries."
                  ::= { bladeMACAddressVpdEntry 17 }

      bladeDaughterCard2MACAddress1Vpd  OBJECT-TYPE
                  SYNTAX  OCTET STRING
                  ACCESS  read-only
                  STATUS  mandatory
                  DESCRIPTION
                  "Blade expansion card (daughter card) 2 MAC address 1.
                  For consistent results, view as a table and not as individual entries."
                  ::= { bladeMACAddressVpdEntry 18 }

      bladeDaughterCard2MACAddress2Vpd  OBJECT-TYPE
                  SYNTAX  OCTET STRING
                  ACCESS  read-only
                  STATUS  mandatory
                  DESCRIPTION
                  "Blade expansion card (daughter card) 2 MAC address 2.
                  For consistent results, view as a table and not as individual entries."
                  ::= { bladeMACAddressVpdEntry 19 }

      bladeDaughterCard2MACAddress3Vpd  OBJECT-TYPE
                  SYNTAX  OCTET STRING
                  ACCESS  read-only
                  STATUS  mandatory
                  DESCRIPTION
                  "Blade expansion card (daughter card) 2 MAC address 3.
                  For consistent results, view as a table and not as individual entries."
                  ::= { bladeMACAddressVpdEntry 20 }

      bladeDaughterCard2MACAddress4Vpd  OBJECT-TYPE
                  SYNTAX  OCTET STRING
                  ACCESS  read-only
                  STATUS  mandatory
                  DESCRIPTION
                  "Blade expansion card (daughter card) 2 MAC address 4.
                  For consistent results, view as a table and not as individual entries."
                  ::= { bladeMACAddressVpdEntry 21 }

      bladeDaughterCard2MACAddress5Vpd  OBJECT-TYPE
                  SYNTAX  OCTET STRING
                  ACCESS  read-only
                  STATUS  mandatory
                  DESCRIPTION
                  "Blade expansion card (daughter card) 2 MAC address 5.
                  For consistent results, view as a table and not as individual entries."
                  ::= { bladeMACAddressVpdEntry 22 }

      bladeDaughterCard2MACAddress6Vpd  OBJECT-TYPE
                  SYNTAX  OCTET STRING
                  ACCESS  read-only
                  STATUS  mandatory
                  DESCRIPTION
                  "Blade expansion card (daughter card) 2 MAC address 6.
                  For consistent results, view as a table and not as individual entries."
                  ::= { bladeMACAddressVpdEntry 23 }

      bladeDaughterCard2MACAddress7Vpd  OBJECT-TYPE
                  SYNTAX  OCTET STRING
                  ACCESS  read-only
                  STATUS  mandatory
                  DESCRIPTION
                  "Blade expansion card (daughter card) 2 MAC address 7.
                  For consistent results, view as a table and not as individual entries."
                  ::= { bladeMACAddressVpdEntry 24 }

      bladeDaughterCard2MACAddress8Vpd  OBJECT-TYPE
                  SYNTAX  OCTET STRING
                  ACCESS  read-only
                  STATUS  mandatory
                  DESCRIPTION
                  "Blade expansion card (daughter card) 2 MAC address 8.
                  For consistent results, view as a table and not as individual entries."
                  ::= { bladeMACAddressVpdEntry 25 }

      bladeDaughterCard3MACAddress1Vpd  OBJECT-TYPE
                  SYNTAX  OCTET STRING
                  ACCESS  read-only
                  STATUS  mandatory
                  DESCRIPTION
                  "Blade expansion card (daughter card) 3 MAC address 1.
                  For consistent results, view as a table and not as individual entries."
                  ::= { bladeMACAddressVpdEntry 26 }

      bladeDaughterCard3MACAddress2Vpd  OBJECT-TYPE
                  SYNTAX  OCTET STRING
                  ACCESS  read-only
                  STATUS  mandatory
                  DESCRIPTION
                  "Blade expansion card (daughter card) 3 MAC address 2.
                  For consistent results, view as a table and not as individual entries."
                  ::= { bladeMACAddressVpdEntry 27 }

      bladeDaughterCard3MACAddress3Vpd  OBJECT-TYPE
                  SYNTAX  OCTET STRING
                  ACCESS  read-only
                  STATUS  mandatory
                  DESCRIPTION
                  "Blade expansion card (daughter card) 3 MAC address 3.
                  For consistent results, view as a table and not as individual entries."
                  ::= { bladeMACAddressVpdEntry 28 }

      bladeDaughterCard3MACAddress4Vpd  OBJECT-TYPE
                  SYNTAX  OCTET STRING
                  ACCESS  read-only
                  STATUS  mandatory
                  DESCRIPTION
                  "Blade expansion card (daughter card) 3 MAC address 4.
                  For consistent results, view as a table and not as individual entries."
                  ::= { bladeMACAddressVpdEntry 29 }

      bladeDaughterCard3MACAddress5Vpd  OBJECT-TYPE
                  SYNTAX  OCTET STRING
                  ACCESS  read-only
                  STATUS  mandatory
                  DESCRIPTION
                  "Blade expansion card (daughter card) 3 MAC address 5.
                  For consistent results, view as a table and not as individual entries."
                  ::= { bladeMACAddressVpdEntry 30 }

      bladeDaughterCard3MACAddress6Vpd  OBJECT-TYPE
                  SYNTAX  OCTET STRING
                  ACCESS  read-only
                  STATUS  mandatory
                  DESCRIPTION
                  "Blade expansion card (daughter card) 3 MAC address 6.
                  For consistent results, view as a table and not as individual entries."
                  ::= { bladeMACAddressVpdEntry 31 }

      bladeDaughterCard3MACAddress7Vpd  OBJECT-TYPE
                  SYNTAX  OCTET STRING
                  ACCESS  read-only
                  STATUS  mandatory
                  DESCRIPTION
                  "Blade expansion card (daughter card) 3 MAC address 7.
                  For consistent results, view as a table and not as individual entries."
                  ::= { bladeMACAddressVpdEntry 32 }

      bladeDaughterCard3MACAddress8Vpd  OBJECT-TYPE
                  SYNTAX  OCTET STRING
                  ACCESS  read-only
                  STATUS  mandatory
                  DESCRIPTION
                  "Blade expansion card (daughter card) 3 MAC address 8.
                  For consistent results, view as a table and not as individual entries."
                  ::= { bladeMACAddressVpdEntry 33 }

      bladeDaughterCard4MACAddress1Vpd  OBJECT-TYPE
                  SYNTAX  OCTET STRING
                  ACCESS  read-only
                  STATUS  mandatory
                  DESCRIPTION
                  "Blade expansion card (daughter card) 4 MAC address 1.
                  For consistent results, view as a table and not as individual entries."
                  ::= { bladeMACAddressVpdEntry 34 }

      bladeDaughterCard4MACAddress2Vpd  OBJECT-TYPE
                  SYNTAX  OCTET STRING
                  ACCESS  read-only
                  STATUS  mandatory
                  DESCRIPTION
                  "Blade expansion card (daughter card) 4 MAC address 2.
                  For consistent results, view as a table and not as individual entries."
                  ::= { bladeMACAddressVpdEntry 35 }

      bladeDaughterCard4MACAddress3Vpd  OBJECT-TYPE
                  SYNTAX  OCTET STRING
                  ACCESS  read-only
                  STATUS  mandatory
                  DESCRIPTION
                  "Blade expansion card (daughter card) 4 MAC address 3.
                  For consistent results, view as a table and not as individual entries."
                  ::= { bladeMACAddressVpdEntry 36 }

      bladeDaughterCard4MACAddress4Vpd  OBJECT-TYPE
                  SYNTAX  OCTET STRING
                  ACCESS  read-only
                  STATUS  mandatory
                  DESCRIPTION
                  "Blade expansion card (daughter card) 4 MAC address 4.
                  For consistent results, view as a table and not as individual entries."
                  ::= { bladeMACAddressVpdEntry 37 }

      bladeDaughterCard4MACAddress5Vpd  OBJECT-TYPE
                  SYNTAX  OCTET STRING
                  ACCESS  read-only
                  STATUS  mandatory
                  DESCRIPTION
                  "Blade expansion card (daughter card) 4 MAC address 5.
                  For consistent results, view as a table and not as individual entries."
                  ::= { bladeMACAddressVpdEntry 38 }

      bladeDaughterCard4MACAddress6Vpd  OBJECT-TYPE
                  SYNTAX  OCTET STRING
                  ACCESS  read-only
                  STATUS  mandatory
                  DESCRIPTION
                  "Blade expansion card (daughter card) 4 MAC address 6.
                  For consistent results, view as a table and not as individual entries."
                  ::= { bladeMACAddressVpdEntry 39 }

      bladeDaughterCard4MACAddress7Vpd  OBJECT-TYPE
                  SYNTAX  OCTET STRING
                  ACCESS  read-only
                  STATUS  mandatory
                  DESCRIPTION
                  "Blade expansion card (daughter card) 4 MAC address 7.
                  For consistent results, view as a table and not as individual entries."
                  ::= { bladeMACAddressVpdEntry 40 }

      bladeDaughterCard4MACAddress8Vpd  OBJECT-TYPE
                  SYNTAX  OCTET STRING
                  ACCESS  read-only
                  STATUS  mandatory
                  DESCRIPTION
                  "Blade expansion card (daughter card) 4 MAC address 8.
                  For consistent results, view as a table and not as individual entries."
                  ::= { bladeMACAddressVpdEntry 41 }

      bladeDaughterCard5MACAddress1Vpd  OBJECT-TYPE
                  SYNTAX  OCTET STRING
                  ACCESS  read-only
                  STATUS  mandatory
                  DESCRIPTION
                  "Blade expansion card (daughter card) 5 MAC address 1.
                  For consistent results, view as a table and not as individual entries."
                  ::= { bladeMACAddressVpdEntry 42 }

      bladeDaughterCard5MACAddress2Vpd  OBJECT-TYPE
                  SYNTAX  OCTET STRING
                  ACCESS  read-only
                  STATUS  mandatory
                  DESCRIPTION
                  "Blade expansion card (daughter card) 5 MAC address 2.
                  For consistent results, view as a table and not as individual entries."
                  ::= { bladeMACAddressVpdEntry 43 }

      bladeDaughterCard5MACAddress3Vpd  OBJECT-TYPE
                  SYNTAX  OCTET STRING
                  ACCESS  read-only
                  STATUS  mandatory
                  DESCRIPTION
                  "Blade expansion card (daughter card) 5 MAC address 3.
                  For consistent results, view as a table and not as individual entries."
                  ::= { bladeMACAddressVpdEntry 44}

      bladeDaughterCard5MACAddress4Vpd  OBJECT-TYPE
                  SYNTAX  OCTET STRING
                  ACCESS  read-only
                  STATUS  mandatory
                  DESCRIPTION
                  "Blade expansion card (daughter card) 5 MAC address 4.
                  For consistent results, view as a table and not as individual entries."
                  ::= { bladeMACAddressVpdEntry 45 }

      bladeDaughterCard5MACAddress5Vpd  OBJECT-TYPE
                  SYNTAX  OCTET STRING
                  ACCESS  read-only
                  STATUS  mandatory
                  DESCRIPTION
                  "Blade expansion card (daughter card) 5 MAC address 5.
                  For consistent results, view as a table and not as individual entries."
                  ::= { bladeMACAddressVpdEntry 46 }

      bladeDaughterCard5MACAddress6Vpd  OBJECT-TYPE
                  SYNTAX  OCTET STRING
                  ACCESS  read-only
                  STATUS  mandatory
                  DESCRIPTION
                  "Blade expansion card (daughter card) 5 MAC address 6.
                  For consistent results, view as a table and not as individual entries."
                  ::= { bladeMACAddressVpdEntry 47 }

      bladeDaughterCard5MACAddress7Vpd  OBJECT-TYPE
                  SYNTAX  OCTET STRING
                  ACCESS  read-only
                  STATUS  mandatory
                  DESCRIPTION
                  "Blade expansion card (daughter card) 5 MAC address 7.
                  For consistent results, view as a table and not as individual entries."
                  ::= { bladeMACAddressVpdEntry 48 }

      bladeDaughterCard5MACAddress8Vpd  OBJECT-TYPE
                  SYNTAX  OCTET STRING
                  ACCESS  read-only
                  STATUS  mandatory
                  DESCRIPTION
                  "Blade expansion card (daughter card) 5 MAC address 8.
                  For consistent results, view as a table and not as individual entries."
                  ::= { bladeMACAddressVpdEntry 49 }

      bladeHSDaughterCard1MACAddress1Vpd  OBJECT-TYPE
                  SYNTAX  OCTET STRING
                  ACCESS  read-only
                  STATUS  mandatory
                  DESCRIPTION
                  "Blade high speed expansion card (daughter card) 1 MAC address 1.
                  For consistent results, view  as a table and not as individual entries."
                  ::= { bladeMACAddressVpdEntry 100 }

      bladeHSDaughterCard1MACAddress2Vpd  OBJECT-TYPE
                  SYNTAX  OCTET STRING
                  ACCESS  read-only
                  STATUS  mandatory
                  DESCRIPTION
                  "Blade high speed expansion card (daughter card) 1 MAC address 2.
                  For consistent results, view as a table and not as individual entries."
                  ::= { bladeMACAddressVpdEntry 101 }

      bladeHSDaughterCard1MACAddress3Vpd  OBJECT-TYPE
                  SYNTAX  OCTET STRING
                  ACCESS  read-only
                  STATUS  mandatory
                  DESCRIPTION
                  "Blade high speed expansion card (daughter card) 1 MAC address 3.
                  For consistent results, view as a table and not as individual entries."
                  ::= { bladeMACAddressVpdEntry 102}

      bladeHSDaughterCard1MACAddress4Vpd  OBJECT-TYPE
                  SYNTAX  OCTET STRING
                  ACCESS  read-only
                  STATUS  mandatory
                  DESCRIPTION
                  "Blade high speed expansion card (daughter card) 1 MAC address 4.
                  For consistent results, view as a table and not as individual entries."
                  ::= { bladeMACAddressVpdEntry 103 }

      bladeHSDaughterCard1MACAddress5Vpd  OBJECT-TYPE
                  SYNTAX  OCTET STRING
                  ACCESS  read-only
                  STATUS  mandatory
                  DESCRIPTION
                  "Blade high speed expansion card (daughter card) 1 MAC address 5.
                  For consistent results, view as a table and not as individual entries."
                  ::= { bladeMACAddressVpdEntry 104 }

      bladeHSDaughterCard1MACAddress6Vpd  OBJECT-TYPE
                  SYNTAX  OCTET STRING
                  ACCESS  read-only
                  STATUS  mandatory
                  DESCRIPTION
                  "Blade high speed expansion card (daughter card) 1 MAC address 6.
                  For consistent results, view as a table and not as individual entries."
                  ::= { bladeMACAddressVpdEntry 105 }

      bladeHSDaughterCard1MACAddress7Vpd  OBJECT-TYPE
                  SYNTAX  OCTET STRING
                  ACCESS  read-only
                  STATUS  mandatory
                  DESCRIPTION
                  "Blade high speed expansion card (daughter card) 1 MAC address 7.
                  For consistent results, view as a table and not as individual entries."
                  ::= { bladeMACAddressVpdEntry 106 }

      bladeHSDaughterCard1MACAddress8Vpd  OBJECT-TYPE
                  SYNTAX  OCTET STRING
                  ACCESS  read-only
                  STATUS  mandatory
                  DESCRIPTION
                  "Blade high speed expansion card (daughter card) 1 MAC address 8.
                  For consistent results, view as a table and not as individual entries."
                  ::= { bladeMACAddressVpdEntry 107 }

      bladeSideCardMACAddress1Vpd  OBJECT-TYPE
                  SYNTAX  OCTET STRING
                  ACCESS  read-only
                  STATUS  mandatory
                  DESCRIPTION
                  "Blade side card MAC address 1.
                  For consistent results, view as a table and not as individual entries."
                  ::= { bladeMACAddressVpdEntry 164 }

      bladeSideCardMACAddress2Vpd  OBJECT-TYPE
                  SYNTAX  OCTET STRING
                  ACCESS  read-only
                  STATUS  mandatory
                  DESCRIPTION
                  "Blade side card MAC address 2.
                  For consistent results, view as a table and not as individual entries."
                  ::= { bladeMACAddressVpdEntry 165 }

      bladeSideCardMACAddress3Vpd  OBJECT-TYPE
                  SYNTAX  OCTET STRING
                  ACCESS  read-only
                  STATUS  mandatory
                  DESCRIPTION
                  "Blade side card MAC address 3.
                  For consistent results, view as a table and not as individual entries."
                  ::= { bladeMACAddressVpdEntry 166 }

      bladeSideCardMACAddress4Vpd  OBJECT-TYPE
                  SYNTAX  OCTET STRING
                  ACCESS  read-only
                  STATUS  mandatory
                  DESCRIPTION
                  "Blade side card MAC address 4.
                  For consistent results, view as a table and not as individual entries."
                  ::= { bladeMACAddressVpdEntry 167 }

      bladeSideCardMACAddress5Vpd  OBJECT-TYPE
                  SYNTAX  OCTET STRING
                  ACCESS  read-only
                  STATUS  mandatory
                  DESCRIPTION
                  "Blade side card MAC address 5.
                  For consistent results, view as a table and not as individual entries."
                  ::= { bladeMACAddressVpdEntry 168 }

      bladeSideCardMACAddress6Vpd  OBJECT-TYPE
                  SYNTAX  OCTET STRING
                  ACCESS  read-only
                  STATUS  mandatory
                  DESCRIPTION
                  "Blade side card MAC address 6.
                  For consistent results, view as a table and not as individual entries."
                  ::= { bladeMACAddressVpdEntry 169 }

      bladeSideCardMACAddress7Vpd  OBJECT-TYPE
                  SYNTAX  OCTET STRING
                  ACCESS  read-only
                  STATUS  mandatory
                  DESCRIPTION
                  "Blade side card MAC address 7.
                  For consistent results, view as a table and not as individual entries."
                  ::= { bladeMACAddressVpdEntry 170 }

      bladeSideCardMACAddress8Vpd  OBJECT-TYPE
                  SYNTAX  OCTET STRING
                  ACCESS  read-only
                  STATUS  mandatory
                  DESCRIPTION
                  "Blade side card MAC address 8.
                  For consistent results, view as a table and not as individual entries."
                  ::= { bladeMACAddressVpdEntry 171 }

      -- ********************************************************************************
      -- Blade Expansion Card VPD
      -- ********************************************************************************

      bladeExpCardVpdTable OBJECT-TYPE
                    SYNTAX  SEQUENCE OF BladeExpCardVpdEntry
                    ACCESS  not-accessible
                    STATUS  deprecated
                    DESCRIPTION
                    "Table of VPD information for the blade expansion card components.
                    For consistent results, view as a table and not as individual entries."
                    ::= { bladeHardwareVpd 5 }

      bladeExpCardVpdEntry OBJECT-TYPE
                    SYNTAX BladeExpCardVpdEntry
                    ACCESS  not-accessible
                    STATUS  deprecated
                    DESCRIPTION
                    "Blade expansion card VPD entry.
                    For consistent results, view as a table and not as individual entries."
                    INDEX { bladeExpCardVpdIndex }
                    ::= { bladeExpCardVpdTable 1 }

      BladeExpCardVpdEntry ::= SEQUENCE {
                  bladeExpCardVpdIndex INTEGER,
                  bladeExpCardVpdBayNumber OCTET STRING,
                  bladeExpCardVpdManufacturingId OCTET STRING,
                  bladeExpCardVpdFruNumber OCTET STRING,
                  bladeExpCardVpdHardwareRevision INTEGER,
                  bladeExpCardVpdSerialNumber OCTET STRING,
                  bladeExpCardVpdMachineType OCTET STRING,
                  bladeExpCardVpdUuid OCTET STRING,
                  bladeExpCardVpdManufDate OCTET STRING,
                  bladeExpCardVpdPartNumber OCTET STRING,
                  bladeExpCardVpdFruSerial OCTET STRING,
                  bladeExpCardVpdMachineModel OCTET STRING,
                  bladeExpCardVpdManufacturingIDNumber OCTET STRING,
                  bladeExpCardVpdProductId OCTET STRING,
                  bladeExpCardVpdSubManufacturerId OCTET STRING,
                  bladeExpCardVpdClei OCTET STRING,
                  bladeExpCardVpdBladeBayNumber OCTET STRING,
                  bladeExpCardVpdCardTypeInfo INTEGER,
                  bladeExpCardVpdHighSpeed INTEGER,
                  bladeExpCardVpdHardwareRevisionString OCTET STRING
                  }

      bladeExpCardVpdIndex  OBJECT-TYPE
                  SYNTAX  INTEGER
                  ACCESS  read-only
                  STATUS  deprecated
                  DESCRIPTION
                  "Blade expansion card VPD index.
                  For consistent results, view as a table and not as individual entries."
                  ::= { bladeExpCardVpdEntry 1 }

      bladeExpCardVpdBayNumber  OBJECT-TYPE
                  SYNTAX  OCTET STRING
                  ACCESS  read-only
                  STATUS  deprecated
                  DESCRIPTION
                  "Blade expansion card VPD Bay number.
                  For consistent results, view as a table and not as individual entries."
                  ::= { bladeExpCardVpdEntry 2 }

      bladeExpCardVpdManufacturingId  OBJECT-TYPE
                  SYNTAX  OCTET STRING
                  ACCESS  read-only
                  STATUS  deprecated
                  DESCRIPTION
                  "Blade expansion card VPD manufacturing ID.
                  For consistent results, view as a table and not as individual entries."
                  ::= { bladeExpCardVpdEntry 3 }

      bladeExpCardVpdFruNumber  OBJECT-TYPE
                  SYNTAX  OCTET STRING
                  ACCESS  read-only
                  STATUS  deprecated
                  DESCRIPTION
                  "Blade expansion card VPD FRU number.
                  For consistent results, view as a table and not as individual entries."
                  ::= { bladeExpCardVpdEntry 4 }

      bladeExpCardVpdHardwareRevision  OBJECT-TYPE
                  SYNTAX  INTEGER
                  ACCESS  read-only
                  STATUS  deprecated
                  DESCRIPTION
                  "Blade expansion card VPD hardware revision.
                  For consistent results, view as a table and not as individual entries.
                  If a hardware revision is programmed in the OEM VPD area for this component,
                  then the HardwareRevisionString version of this MIB object should be used."
                  ::= { bladeExpCardVpdEntry 5 }

      bladeExpCardVpdSerialNumber  OBJECT-TYPE
                  SYNTAX  OCTET STRING
                  ACCESS  read-only
                  STATUS  deprecated
                  DESCRIPTION
                  "Blade expansion card VPD serial number.
                  For consistent results, view as a table and not as individual entries."
                  ::= { bladeExpCardVpdEntry 6 }

      bladeExpCardVpdMachineType  OBJECT-TYPE
                  SYNTAX  OCTET STRING
                  ACCESS  read-only
                  STATUS  deprecated
                  DESCRIPTION
                  "Blade expansion card VPD machine type.
                  For consistent results, view as a table and not as individual entries."
                  ::= { bladeExpCardVpdEntry 7 }

      bladeExpCardVpdUuid  OBJECT-TYPE
                  SYNTAX  OCTET STRING
                  ACCESS  read-only
                  STATUS  deprecated
                  DESCRIPTION
                  "Blade expansion card VPD UUID.
                  For consistent results, view as a table and not as individual entries."
                  ::= { bladeExpCardVpdEntry 8 }

      bladeExpCardVpdManufDate  OBJECT-TYPE
                  SYNTAX  OCTET STRING
                  ACCESS  read-only
                  STATUS  deprecated
                  DESCRIPTION
                  "Blade expansion card VPD Manufacture Date.
                  For consistent results, view as a table and not as individual entries."
                  ::= { bladeExpCardVpdEntry 9 }

      bladeExpCardVpdPartNumber  OBJECT-TYPE
                  SYNTAX  OCTET STRING
                  ACCESS  read-only
                  STATUS  deprecated
                  DESCRIPTION
                  "Blade expansion card VPD Part number.
                  For consistent results, view as a table and not as individual entries."
                  ::= { bladeExpCardVpdEntry 10 }

      bladeExpCardVpdFruSerial  OBJECT-TYPE
                  SYNTAX  OCTET STRING
                  ACCESS  read-only
                  STATUS  deprecated
                  DESCRIPTION
                  "Blade expansion card VPD FRU serial number.
                  For consistent results, view as a table and not as individual entries."
                  ::= { bladeExpCardVpdEntry 11 }

       bladeExpCardVpdMachineModel  OBJECT-TYPE
                  SYNTAX  OCTET STRING
                  ACCESS  read-only
                  STATUS  deprecated
                  DESCRIPTION
                  "Blade expansion card VPD machine model.
                  For consistent results, view as a table and not as individual entries."
                  ::= { bladeExpCardVpdEntry 12 }

      bladeExpCardVpdManufacturingIDNumber  OBJECT-TYPE
                  SYNTAX  OCTET STRING
                  ACCESS  read-only
                  STATUS  deprecated
                  DESCRIPTION
                  "Blade expansion card VPD Manufacturer ID Number.
                  For consistent results, view as a table and not as individual entries."
                  ::= { bladeExpCardVpdEntry 13 }

      bladeExpCardVpdProductId OBJECT-TYPE
                  SYNTAX  OCTET STRING
                  ACCESS  read-only
                  STATUS  deprecated
                  DESCRIPTION
                  "Blade expansion card VPD Product ID.
                  For consistent results, view as a table and not as individual entries."
                  ::= { bladeExpCardVpdEntry 14 }

      bladeExpCardVpdSubManufacturerId  OBJECT-TYPE
                  SYNTAX  OCTET STRING
                  ACCESS  read-only
                  STATUS  deprecated
                  DESCRIPTION
                  "Blade expansion card VPD subsystem manufacturer ID.
                  For consistent results, view as a table and not as individual entries."
                  ::= { bladeExpCardVpdEntry 15 }

      bladeExpCardVpdClei  OBJECT-TYPE
                  SYNTAX  OCTET STRING
                  ACCESS  read-only
                  STATUS  deprecated
                  DESCRIPTION
                  "Blade expansion card VPD Common Language Equipment Identifier (CLEI).
                  For consistent results, view as a table and not as individual entries."
                  ::= { bladeExpCardVpdEntry 16 }

       bladeExpCardVpdBladeBayNumber  OBJECT-TYPE
                  SYNTAX  OCTET STRING
                  ACCESS  read-only
                  STATUS  deprecated
                  DESCRIPTION
                  "Blade bay number of the blade expansion card.
                  For consistent results, view as a table and not as individual entries."
                  ::= { bladeExpCardVpdEntry 19 }

       bladeExpCardVpdCardTypeInfo  OBJECT-TYPE
                  SYNTAX  INTEGER  {
                    unknown(0),
                    bladeEthernetExpCard(1),
                    bladeFiberChannelExpCard(2),
                    serialPortExpCard(3),
                    bladeOpticalPassThrough(4),
                    bladeInfinibandExpCard(5),
                    bladeIscsiExpCard(6),
                    bladeGenericExpCard(7),
                    bladeNetworkCFFeExpCard(8),
                    bladeSASConnectivityCard(9),
                    bladeSATAConnectivityCard(10),
                    bladeNetworkCFFzExpCard(11),
                    bladeNetworkCNAExpCard(12)
                  }
                  ACCESS  read-only
                  STATUS  deprecated
                  DESCRIPTION
                  "Blade expansion card (daughter card) VPD type code that describes the expansion
                  card.  For consistent results, view as a table and not as individual entries.

                  NOTE: The CFFe expansion card is also referred to as a CFFh expansion card."
                  ::= { bladeExpCardVpdEntry 21 }

       bladeExpCardVpdHighSpeed  OBJECT-TYPE
                  SYNTAX  INTEGER  {
                    no(0),
                    yes(1),
                    notApplicable(255)
                  }
                  ACCESS  read-only
                  STATUS  deprecated
                  DESCRIPTION
                  "Blade expansion card (daughter card) VPD high speed that indicates whether the
                  expansion card is high speed or not.  For consistent results, view as a table and
                  not as individual entries."
                  ::= { bladeExpCardVpdEntry 22 }

      bladeExpCardVpdHardwareRevisionString  OBJECT-TYPE
                  SYNTAX  OCTET STRING
                  ACCESS  read-only
                  STATUS  deprecated
                  DESCRIPTION
                  "Blade expansion card VPD hardware revision in string format.
                  For consistent results, view as a table and not as individual entries.
                  If a hardware revision is programmed in the OEM VPD area for this component,
                  then this MIB object should be used."
                  ::= { bladeExpCardVpdEntry 23 }

      -- ********************************************************************************
      -- Blade and expansion card WWN/GUIDs
      -- ********************************************************************************
        bladeAndExpCardWwnGuidVpdTable OBJECT-TYPE
                    SYNTAX  SEQUENCE OF BladeAndExpCardWwnGuidVpdEntry
                    ACCESS  not-accessible
                    STATUS  deprecated
                    DESCRIPTION
                    "Table of World Wide Names (WWN), Global Unique IDs (GUID) and
                    Serial Attach SCSI IDs (SAS) of the blade server and its expansion
                    cards (daughter cards).
                    For consistent results, view as a table and not as individual entries."
                    ::= { bladeHardwareVpd 7 }

        bladeAndExpCardWwnGuidVpdEntry OBJECT-TYPE
                    SYNTAX  BladeAndExpCardWwnGuidVpdEntry
                    ACCESS  not-accessible

                    STATUS  deprecated
                    DESCRIPTION
                    "Blade WWN/GUID entries.
                    For consistent results, view as a table and not as individual entries."
                    INDEX { bladeAndExpCardWwnGuidVpdIndex }
                    ::= { bladeAndExpCardWwnGuidVpdTable 1 }

        BladeAndExpCardWwnGuidVpdEntry ::= SEQUENCE {
                    bladeAndExpCardWwnGuidVpdIndex INTEGER,
                    bladeAndExpCardWwnGuidVpdBayNumber OCTET STRING,
                    bladeAndExpCardWwnGuidVpdName OCTET STRING,
                    bladeAndExpCardWwnGuidVpdBladeBayNumber OCTET STRING,
                    bladeAndExpCardWwnGuidVpdType INTEGER,
                    bladeAndExpCardWwnGuidVpd1 OCTET STRING,
                    bladeAndExpCardWwnGuidVpd2 OCTET STRING,
                    bladeAndExpCardWwnGuidVpd3 OCTET STRING,
                    bladeAndExpCardWwnGuidVpd4 OCTET STRING,
                    bladeAndExpCardWwnGuidVpd5 OCTET STRING,
                    bladeAndExpCardWwnGuidVpd6 OCTET STRING,
                    bladeAndExpCardWwnGuidVpd7 OCTET STRING,
                    bladeAndExpCardWwnGuidVpd8 OCTET STRING
                    }

        bladeAndExpCardWwnGuidVpdIndex  OBJECT-TYPE
                    SYNTAX  INTEGER
                    ACCESS  read-only
                    STATUS  deprecated
                    DESCRIPTION
                    "Blade or expansion card index.
                    For consistent results, view as a table and not as individual entries."
                    ::= { bladeAndExpCardWwnGuidVpdEntry 1 }

        bladeAndExpCardWwnGuidVpdBayNumber  OBJECT-TYPE
                    SYNTAX  OCTET STRING
                    ACCESS  read-only
                    STATUS  deprecated
                    DESCRIPTION
                    "Blade or expansion card VPD bay number.
                    For consistent results, view as a table and not as individual entries."
                    ::= { bladeAndExpCardWwnGuidVpdEntry 2 }

        bladeAndExpCardWwnGuidVpdName  OBJECT-TYPE
                    SYNTAX  OCTET STRING
                    ACCESS  read-only
                    STATUS  deprecated
                    DESCRIPTION
                    "The name of the blade or expansion card.
                    For consistent results, view as a table and not as individual entries."
                    ::= { bladeAndExpCardWwnGuidVpdEntry 3 }

        bladeAndExpCardWwnGuidVpdBladeBayNumber  OBJECT-TYPE
                    SYNTAX  OCTET STRING
                    ACCESS  read-only
                    STATUS  deprecated
                    DESCRIPTION
                    "For expansion cards, it's the blade bay number of the blade
                    expansion card. For blades, it's the bay number of the blade.
                    For consistent results, view as a table and not as individual entries."
                    ::= { bladeAndExpCardWwnGuidVpdEntry 4 }

        bladeAndExpCardWwnGuidVpdType  OBJECT-TYPE
                    SYNTAX  INTEGER  {
                      notAvailable(0),
                      wwn(1),
                      guid(2),
                      sas(3)
                    }
                    ACCESS  read-only
                    STATUS  deprecated
                    DESCRIPTION
                    "Blade or expansion card WWN/GUID/SAS Type.
                    For consistent results, view as a table and not as individual entries."
                    ::= { bladeAndExpCardWwnGuidVpdEntry 5 }

        bladeAndExpCardWwnGuidVpd1  OBJECT-TYPE
                    SYNTAX  OCTET STRING
                    ACCESS  read-only
                    STATUS  deprecated
                    DESCRIPTION
                    "Blade or expansion card WWN/GUID 1.
                    For consistent results, view as a table and not as individual entries."
                    ::= { bladeAndExpCardWwnGuidVpdEntry 6 }

        bladeAndExpCardWwnGuidVpd2  OBJECT-TYPE
                    SYNTAX  OCTET STRING
                    ACCESS  read-only
                    STATUS  deprecated
                    DESCRIPTION
                    "Blade or expansion card WWN/GUID 2.
                    For consistent results, view as a table and not as individual entries."
                    ::= { bladeAndExpCardWwnGuidVpdEntry 7 }

        bladeAndExpCardWwnGuidVpd3  OBJECT-TYPE
                    SYNTAX  OCTET STRING
                    ACCESS  read-only
                    STATUS  deprecated
                    DESCRIPTION
                    "Blade or expansion card WWN/GUID 3.
                    For consistent results, view as a table and not as individual entries."
                    ::= { bladeAndExpCardWwnGuidVpdEntry 8 }

        bladeAndExpCardWwnGuidVpd4  OBJECT-TYPE
                    SYNTAX  OCTET STRING
                    ACCESS  read-only
                    STATUS  deprecated
                    DESCRIPTION
                    "Blade or expansion card WWN/GUID 4.
                    For consistent results, view as a table and not as individual entries."
                    ::= { bladeAndExpCardWwnGuidVpdEntry 9 }

        bladeAndExpCardWwnGuidVpd5  OBJECT-TYPE
                    SYNTAX  OCTET STRING
                    ACCESS  read-only
                    STATUS  deprecated
                    DESCRIPTION
                    "Blade or expansion card WWN/GUID 5.
                    For consistent results, view as a table and not as individual entries."
                    ::= { bladeAndExpCardWwnGuidVpdEntry 10 }

        bladeAndExpCardWwnGuidVpd6  OBJECT-TYPE
                    SYNTAX  OCTET STRING
                    ACCESS  read-only
                    STATUS  deprecated
                    DESCRIPTION
                    "Blade or expansion card WWN/GUID 6.
                    For consistent results, view as a table and not as individual entries."
                    ::= { bladeAndExpCardWwnGuidVpdEntry 11 }

        bladeAndExpCardWwnGuidVpd7  OBJECT-TYPE
                    SYNTAX  OCTET STRING
                    ACCESS  read-only
                    STATUS  deprecated
                    DESCRIPTION
                    "Blade or expansion card WWN/GUID 7.
                    For consistent results, view as a table and not as individual entries."
                    ::= { bladeAndExpCardWwnGuidVpdEntry 12 }

        bladeAndExpCardWwnGuidVpd8  OBJECT-TYPE
                    SYNTAX  OCTET STRING
                    ACCESS  read-only
                    STATUS  deprecated
                    DESCRIPTION
                    "Blade or expansion card WWN/GUID 8.
                    For consistent results, view as a table and not as individual entries."
                    ::= { bladeAndExpCardWwnGuidVpdEntry 13 }


      -- ********************************************************************************
      -- Blade managerment card vpd
      -- ********************************************************************************

      bladeManagementCardVpdTable OBJECT-TYPE
                    SYNTAX  SEQUENCE OF BladeManagementCardVpdEntry
                    ACCESS  not-accessible
                    STATUS  deprecated
                    DESCRIPTION
                    "Table of VPD information for the blade
                    management card component.
                    For consistent results, view as a table
                    and not as individual entries."
                    ::= { bladeHardwareVpd 8 }

      bladeManagementCardVpdEntry OBJECT-TYPE
                    SYNTAX  BladeManagementCardVpdEntry
                    ACCESS  not-accessible
                    STATUS  deprecated
                    DESCRIPTION
                    "Blade management card VPD entry.
                    For consistent results, view as a table
                    and not as individual entries."
                    INDEX { bladeManagementCardVpdIndex }
                    ::= { bladeManagementCardVpdTable 1 }

      BladeManagementCardVpdEntry ::= SEQUENCE {
                  bladeManagementCardVpdIndex INTEGER,
                  bladeManagementCardVpdBayNumber OCTET STRING,
                  bladeManagementCardVpdManufacturingId OCTET STRING,
                  bladeManagementCardVpdFruNumber OCTET STRING,
                  bladeManagementCardVpdHardwareRevision INTEGER,
                  bladeManagementCardVpdSerialNumber OCTET STRING,
                  bladeManagementCardVpdMachineType OCTET STRING,
                  bladeManagementCardVpdUuid OCTET STRING,
                  bladeManagementCardVpdManufDate OCTET STRING,
                  bladeManagementCardVpdPartNumber OCTET STRING,
                  bladeManagementCardVpdFruSerial OCTET STRING,
                  bladeManagementCardVpdMachineModel OCTET STRING,
                  bladeManagementCardVpdManufacturingIDNumber OCTET STRING,
                  bladeManagementCardVpdProductId OCTET STRING,
                  bladeManagementCardVpdSubManufacturerId OCTET STRING,
                  bladeManagementCardVpdClei OCTET STRING,
                  bladeManagementCardVpdHardwareRevisionString OCTET STRING
                  }

      bladeManagementCardVpdIndex  OBJECT-TYPE
                  SYNTAX  INTEGER
                  ACCESS  read-only
                  STATUS  deprecated
                  DESCRIPTION
                  "Blade management card VPD index.
                  For consistent results, view as a table
                  and not as individual entries."
                  ::= { bladeManagementCardVpdEntry 1 }

      bladeManagementCardVpdBayNumber  OBJECT-TYPE
                  SYNTAX  OCTET STRING
                  ACCESS  read-only
                  STATUS  deprecated
                  DESCRIPTION
                  "Blade management card VPD Bay number.
                  For consistent results, view as a table and
                  not as individual entries."
                  ::= { bladeManagementCardVpdEntry 2 }

      bladeManagementCardVpdManufacturingId  OBJECT-TYPE
                  SYNTAX  OCTET STRING
                  ACCESS  read-only
                  STATUS  deprecated
                  DESCRIPTION
                  "Blade management card VPD manufacturing ID.
                  For consistent results, view as a table and not as
                  individual entries."
                  ::= { bladeManagementCardVpdEntry 3 }

      bladeManagementCardVpdFruNumber  OBJECT-TYPE
                  SYNTAX  OCTET STRING
                  ACCESS  read-only
                  STATUS  deprecated
                  DESCRIPTION
                  "Blade management card VPD FRU number.
                  For consistent results, view as a table and not
                  as individual entries."
                  ::= { bladeManagementCardVpdEntry 4 }

      bladeManagementCardVpdHardwareRevision  OBJECT-TYPE
                  SYNTAX  INTEGER
                  ACCESS  read-only
                  STATUS  deprecated
                  DESCRIPTION
                  "Blade management card VPD hardware revision.
                  For consistent results, view as a table and not as
                  individual entries.
                  If a hardware revision is programmed in the OEM VPD area for this component,
                  then the HardwareRevisionString version of this MIB object should be used."
                  ::= { bladeManagementCardVpdEntry 5 }

      bladeManagementCardVpdSerialNumber  OBJECT-TYPE
                  SYNTAX  OCTET STRING
                  ACCESS  read-only
                  STATUS  deprecated
                  DESCRIPTION
                  "Blade management card VPD serial number.
                  For consistent results, view as a table and not
                  as individual entries."
                  ::= { bladeManagementCardVpdEntry 6 }

      bladeManagementCardVpdMachineType  OBJECT-TYPE
                  SYNTAX  OCTET STRING
                  ACCESS  read-only
                  STATUS  deprecated
                  DESCRIPTION
                  "Blade management card VPD machine type.
                  For consistent results, view as a table and not
                  as individual entries."
                  ::= { bladeManagementCardVpdEntry 7 }

      bladeManagementCardVpdUuid  OBJECT-TYPE
                  SYNTAX  OCTET STRING
                  ACCESS  read-only
                  STATUS  deprecated
                  DESCRIPTION
                  "Blade management card VPD UUID.
                  For consistent results, view as a table
                  and not as individual entries."
                  ::= { bladeManagementCardVpdEntry 8 }

      bladeManagementCardVpdManufDate  OBJECT-TYPE
                  SYNTAX  OCTET STRING
                  ACCESS  read-only
                  STATUS  deprecated
                  DESCRIPTION
                  "Blade management card VPD Manufacture Date.
                  For consistent results, view as a table and not as
                  individual entries."
                  ::= { bladeManagementCardVpdEntry 9 }

      bladeManagementCardVpdPartNumber  OBJECT-TYPE
                  SYNTAX  OCTET STRING
                  ACCESS  read-only
                  STATUS  deprecated
                  DESCRIPTION
                  "Blade management card VPD Part number.
                  For consistent results, view as a table and not
                  as individual entries."
                  ::= { bladeManagementCardVpdEntry 10 }

      bladeManagementCardVpdFruSerial  OBJECT-TYPE
                  SYNTAX  OCTET STRING
                  ACCESS  read-only
                  STATUS  deprecated
                  DESCRIPTION
                  "Blade management card VPD FRU serial number.
                  For consistent results, view as a table and not as
                  individual entries."
                  ::= { bladeManagementCardVpdEntry 11 }

      bladeManagementCardVpdMachineModel  OBJECT-TYPE
                  SYNTAX  OCTET STRING
                  ACCESS  read-only
                  STATUS  deprecated
                  DESCRIPTION
                  "Blade management card VPD machine model.
                  For consistent results, view as a table and not
                  as individual entries."
                  ::= { bladeManagementCardVpdEntry 12 }

      bladeManagementCardVpdManufacturingIDNumber OBJECT-TYPE
                  SYNTAX  OCTET STRING
                  ACCESS  read-only
                  STATUS  deprecated
                  DESCRIPTION
                  "Blade management card VPD manufacturer ID.
                  For consistent results, view as a table and not as
                  individual entries."
                  ::= { bladeManagementCardVpdEntry 13 }

      bladeManagementCardVpdProductId  OBJECT-TYPE
                  SYNTAX  OCTET STRING
                  ACCESS  read-only
                  STATUS  deprecated
                  DESCRIPTION
                  "Blade management card VPD Product ID.
                  For consistent results, view as a table and not
                  as individual entries."
                  ::= { bladeManagementCardVpdEntry 14 }

      bladeManagementCardVpdSubManufacturerId  OBJECT-TYPE
                  SYNTAX  OCTET STRING
                  ACCESS  read-only
                  STATUS  deprecated
                  DESCRIPTION
                  "Blade management card VPD subsystem manufacturer ID.
                  For consistent results, view as a table and not as
                  individual entries."
                  ::= { bladeManagementCardVpdEntry 15 }

      bladeManagementCardVpdClei  OBJECT-TYPE
                  SYNTAX  OCTET STRING
                  ACCESS  read-only
                  STATUS  deprecated
                  DESCRIPTION
                  "Blade management card VPD Common Language Equipment
                  Identifier (CLEI).
                  For consistent results, view as a table and not as
                  individual entries."
                  ::= { bladeManagementCardVpdEntry 16 }

      bladeManagementCardVpdHardwareRevisionString  OBJECT-TYPE
                  SYNTAX  OCTET STRING
                  ACCESS  read-only
                  STATUS  deprecated
                  DESCRIPTION
                  "Blade management card VPD hardware revision in string format.
                  For consistent results, view as a table and not as
                  individual entries.
                  If a hardware revision is programmed in the OEM VPD area for this component,
                  then this MIB object should be used."
                  ::= { bladeManagementCardVpdEntry 17 }

      -- ********************************************************************************
      -- Blade Firmware Level VPD
      -- ********************************************************************************
      bladeFirmwareVpd OBJECT IDENTIFIER ::= { vpdInformation 5 }

      -- ********************************************************************************
      -- Blade BIOS Firmware Level VPD
      -- ********************************************************************************
      bladeBiosVPDTable OBJECT-TYPE
				  SYNTAX  SEQUENCE OF BladeBiosVPDEntry
				  ACCESS  not-accessible
				  STATUS  deprecated
				  DESCRIPTION
				  "Table of blade firmware vital product data (VPD) information."
				  ::= { bladeFirmwareVpd 1 }

      bladeBiosVPDEntry OBJECT-TYPE
				  SYNTAX BladeBiosVPDEntry
				  ACCESS  not-accessible
				  STATUS  deprecated
				  DESCRIPTION
				  "Blade firmware VPD table entry"
				  INDEX { bladeBiosVpdIndex }
				  ::= { bladeBiosVPDTable 1 }

	  BladeBiosVPDEntry ::= SEQUENCE {
				  bladeBiosVpdIndex INTEGER,
				  bladeBiosVpdId INTEGER,
				  bladeBiosVpdExists INTEGER,
				  bladeBiosVpdPowerState INTEGER,
				  bladeBiosVpdName OCTET STRING,
				  bladeBiosVpdBuildId OCTET STRING,
				  bladeBiosVpdRevision OCTET STRING,
				  bladeBiosVpdDate OCTET STRING,
				  bladeBiosVpdLevelStatus  OCTET STRING
				  }

      bladeBiosVpdIndex  OBJECT-TYPE
				  SYNTAX  INTEGER
				  ACCESS  read-only
				  STATUS  deprecated
				  DESCRIPTION
				  "Blade firmware VPD table index."
				  ::= { bladeBiosVPDEntry 1 }

      bladeBiosVpdId  OBJECT-TYPE
				  SYNTAX  INTEGER {
				  blade1(1),
				  blade2(2),
				  blade3(3),
				  blade4(4),
				  blade5(5),
				  blade6(6),
				  blade7(7),
				  blade8(8),
				  blade9(9),
				  blade10(10),
				  blade11(11),
				  blade12(12),
				  blade13(13),
				  blade14(14)
				  }
				  ACCESS  read-only
				  STATUS  deprecated
				  DESCRIPTION
				  "The numeric blade ID."
				  ::= { bladeBiosVPDEntry 2 }

      bladeBiosVpdExists OBJECT-TYPE
				  SYNTAX  INTEGER {
					  false(0),
                                          true(1)
				  }
				  ACCESS  read-only
				  STATUS  deprecated
				  DESCRIPTION
				  "Indicates whether the server blade specified exists or not."
				  ::= { bladeBiosVPDEntry 3 }

      bladeBiosVpdPowerState OBJECT-TYPE
				  SYNTAX  INTEGER {
					  off(0),
                                          on(1),
                                          standby(3),
                                          hibernate(4)
				  }
				  ACCESS  read-only
				  STATUS  deprecated
				  DESCRIPTION
				  "Indicates the power state of the blade specified."
				  ::= { bladeBiosVPDEntry 4 }

      bladeBiosVpdName OBJECT-TYPE
				  SYNTAX  OCTET STRING
				  ACCESS  read-only
				  STATUS  deprecated
				  DESCRIPTION
				  "The name of the blade as a null terminated string."
				  ::= { bladeBiosVPDEntry 5 }

      bladeBiosVpdBuildId OBJECT-TYPE
				  SYNTAX  OCTET STRING
				  ACCESS  read-only
				  STATUS  deprecated
				  DESCRIPTION
				  "The build ID for the blade firmware."
				  ::= { bladeBiosVPDEntry 6 }

      bladeBiosVpdRevision OBJECT-TYPE
				  SYNTAX  OCTET STRING
				  ACCESS  read-only
				  STATUS  deprecated
				  DESCRIPTION
				  "The revision of the blade firmware."
				  ::= { bladeBiosVPDEntry 7 }

      bladeBiosVpdDate OBJECT-TYPE
				  SYNTAX  OCTET STRING
				  ACCESS  read-only
				  STATUS  deprecated
				  DESCRIPTION
				  "The date of the blade firmware."
				  ::= { bladeBiosVPDEntry 8 }

      bladeBiosVpdLevelStatus OBJECT-TYPE
				  SYNTAX  OCTET STRING
				  ACCESS  read-only
				  STATUS  deprecated
				  DESCRIPTION
				  "The level status of the blade bios firmware build ID.
				  It has three possible values as Different (mismatch firmware build ID), Match (the
				  same firmware build ID), Unique (only one such firmware build ID)."
                  ::= { bladeBiosVPDEntry 9 }

      -- ********************************************************************************
      -- Blade DIAGS Firmware Level VPD
      -- ********************************************************************************
      bladeDiagsVPDTable OBJECT-TYPE
				  SYNTAX  SEQUENCE OF BladeDiagsVPDEntry
				  ACCESS  not-accessible
				  STATUS  deprecated
				  DESCRIPTION
				  "Table of blade firmware vital product data (VPD) information."
				  ::= { bladeFirmwareVpd 2 }

      bladeDiagsVPDEntry OBJECT-TYPE
				  SYNTAX BladeDiagsVPDEntry
				  ACCESS  not-accessible
				  STATUS  deprecated
				  DESCRIPTION
				  "Blade firmware VPD table entry"
				  INDEX { bladeDiagsVpdIndex }
				  ::= { bladeDiagsVPDTable 1 }

      BladeDiagsVPDEntry ::= SEQUENCE {
				  bladeDiagsVpdIndex INTEGER,
				  bladeDiagsVpdId INTEGER,
				  bladeDiagsVpdExists INTEGER,
				  bladeDiagsVpdPowerState INTEGER,
				  bladeDiagsVpdName OCTET STRING,
				  bladeDiagsVpdBuildId OCTET STRING,
				  bladeDiagsVpdRevision OCTET STRING,
				  bladeDiagsVpdDate OCTET STRING,
				  bladeDiagsVpdLevelStatus  OCTET STRING
				  }

      bladeDiagsVpdIndex  OBJECT-TYPE
				  SYNTAX  INTEGER
				  ACCESS  read-only
				  STATUS  deprecated
				  DESCRIPTION
				  "Blade firmware VPD table index."
				  ::= { bladeDiagsVPDEntry 1 }

      bladeDiagsVpdId  OBJECT-TYPE
                  SYNTAX  INTEGER {
				  blade1(1),
				  blade2(2),
				  blade3(3),
				  blade4(4),
				  blade5(5),
				  blade6(6),
				  blade7(7),
				  blade8(8),
				  blade9(9),
				  blade10(10),
				  blade11(11),
				  blade12(12),
				  blade13(13),
				  blade14(14)
				  }
				  ACCESS  read-only
				  STATUS  deprecated
				  DESCRIPTION
				  "The numeric blade ID."
				  ::= { bladeDiagsVPDEntry 2 }

      bladeDiagsVpdExists OBJECT-TYPE
				  SYNTAX  INTEGER {
                                      false(0),
                                      true(1)
				  }
				  ACCESS  read-only
				  STATUS  deprecated
				  DESCRIPTION
				  "Indicates whether the server blade specified exists or not."
				  ::= { bladeDiagsVPDEntry 3 }

      bladeDiagsVpdPowerState OBJECT-TYPE
				  SYNTAX  INTEGER {
					  off(0),
                                          on(1),
                                          standby(3),
                                          hibernate(4)
				  }
				  ACCESS  read-only
				  STATUS  deprecated
				  DESCRIPTION
				  "Indicates the power state of the blade specified."
				  ::= { bladeDiagsVPDEntry 4 }

      bladeDiagsVpdName OBJECT-TYPE
				  SYNTAX  OCTET STRING
				  ACCESS  read-only
				  STATUS  deprecated
				  DESCRIPTION
				  "The name of the blade as a null terminated string."
				  ::= { bladeDiagsVPDEntry 5 }

      bladeDiagsVpdBuildId OBJECT-TYPE
				  SYNTAX  OCTET STRING
				  ACCESS  read-only
				  STATUS  deprecated
				  DESCRIPTION
				  "The build ID for the blade firmware."
				  ::= { bladeDiagsVPDEntry 6 }

      bladeDiagsVpdRevision OBJECT-TYPE
				  SYNTAX  OCTET STRING
				  ACCESS  read-only
				  STATUS  deprecated
				  DESCRIPTION
				  "The revision of the blade firmware."
				  ::= { bladeDiagsVPDEntry 7 }

      bladeDiagsVpdDate OBJECT-TYPE
				  SYNTAX  OCTET STRING
				  ACCESS  read-only
				  STATUS  deprecated
				  DESCRIPTION
				  "The date of the blade firmware."
				  ::= { bladeDiagsVPDEntry 8 }

      bladeDiagsVpdLevelStatus OBJECT-TYPE
				  SYNTAX  OCTET STRING
				  ACCESS  read-only
				  STATUS  deprecated
				  DESCRIPTION
				  "The level status of the blade diagnostics firmware build ID.
				  It has three possible values as Different (mismatch firmware build ID), Match (the
				  same firmware build ID), Unique (only one such firmware build ID)."
				  ::= { bladeDiagsVPDEntry 9 }

      -- ********************************************************************************
      -- Blade Mgmt Processor  Firmware Level VPD
      -- ********************************************************************************
      bladeSysMgmtProcVPDTable OBJECT-TYPE
				  SYNTAX  SEQUENCE OF BladeSysMgmtProcVPDEntry
				  ACCESS  not-accessible
				  STATUS  deprecated
				  DESCRIPTION
				  "Table of blade firmware vital product data (VPD) information."
				  ::= { bladeFirmwareVpd 3 }

      bladeSysMgmtProcVPDEntry OBJECT-TYPE
				  SYNTAX BladeSysMgmtProcVPDEntry
				  ACCESS  not-accessible
				  STATUS  deprecated
				  DESCRIPTION
				  "Blade firmware VPD table entry"
				  INDEX { bladeSysMgmtProcVpdIndex }
				  ::= { bladeSysMgmtProcVPDTable 1 }


      BladeSysMgmtProcVPDEntry ::= SEQUENCE {
				  bladeSysMgmtProcVpdIndex INTEGER,
				  bladeSysMgmtProcVpdId INTEGER,
				  bladeSysMgmtProcVpdExists INTEGER,
				  bladeSysMgmtProcVpdPowerState INTEGER,
				  bladeSysMgmtProcVpdName OCTET STRING,
				  bladeSysMgmtProcVpdBuildId OCTET STRING,
				  bladeSysMgmtProcVpdRevision OCTET STRING,
				  bladeSysMgmtProcVpdLevelStatus  OCTET STRING
				  }

      bladeSysMgmtProcVpdIndex  OBJECT-TYPE
				  SYNTAX  INTEGER
				  ACCESS  read-only
				  STATUS  deprecated
				  DESCRIPTION
				  "Blade firmware VPD table index."
				  ::= { bladeSysMgmtProcVPDEntry 1 }


      bladeSysMgmtProcVpdId  OBJECT-TYPE
				  SYNTAX  INTEGER {
					  blade1(1),
					  blade2(2),
                                          blade3(3),
                                          blade4(4),
                                          blade5(5),
                                          blade6(6),
                                          blade7(7),
                                          blade8(8),
                                          blade9(9),
                                          blade10(10),
                                          blade11(11),
                                          blade12(12),
                                          blade13(13),
                                          blade14(14)
				  }
				  ACCESS  read-only
				  STATUS  deprecated
				  DESCRIPTION
				  "The numeric blade ID."
				  ::= { bladeSysMgmtProcVPDEntry 2 }

      bladeSysMgmtProcVpdExists OBJECT-TYPE
				  SYNTAX  INTEGER {
                                        false(0),
                                        true(1)
				  }
				  ACCESS  read-only
				  STATUS  deprecated
				  DESCRIPTION
				  "Indicates whether the server blade specified exists or not."
				  ::= { bladeSysMgmtProcVPDEntry 3 }

      bladeSysMgmtProcVpdPowerState OBJECT-TYPE
				  SYNTAX  INTEGER {
                                        off(0),
                                        on(1),
                                        standby(3),
                                        hibernate(4)
				  }
				  ACCESS  read-only
				  STATUS  deprecated
				  DESCRIPTION
				  "Indicates the power state of the blade specified."
				  ::= { bladeSysMgmtProcVPDEntry 4 }

      bladeSysMgmtProcVpdName OBJECT-TYPE
				  SYNTAX  OCTET STRING
				  ACCESS  read-only
				  STATUS  deprecated
				  DESCRIPTION
				  "The name of the blade as a null terminated string."
				  ::= { bladeSysMgmtProcVPDEntry 5 }

      bladeSysMgmtProcVpdBuildId OBJECT-TYPE
				  SYNTAX  OCTET STRING
				  ACCESS  read-only
				  STATUS  deprecated
				  DESCRIPTION
				  "The build ID for the blade firmware."
				  ::= { bladeSysMgmtProcVPDEntry 6 }

      bladeSysMgmtProcVpdRevision OBJECT-TYPE
				  SYNTAX  OCTET STRING
				  ACCESS  read-only
				  STATUS  deprecated
				  DESCRIPTION
				  "The revision of the blade firmware."
				  ::= { bladeSysMgmtProcVPDEntry 7 }

      bladeSysMgmtProcVpdLevelStatus OBJECT-TYPE
				  SYNTAX  OCTET STRING
				  ACCESS  read-only
				  STATUS  deprecated
				  DESCRIPTION
				  "The level status of the blade system management processor firmware build ID.
				  It has three possible values as Different (mismatch firmware build ID), Match (the
				  same firmware build ID), Unique (only one such firmware build ID)."
				  ::= { bladeSysMgmtProcVPDEntry 8 }

      -- ********************************************************************************
      -- Switch Module Hardware VPD
      -- ********************************************************************************
      smHardwareVpd OBJECT IDENTIFIER ::= { vpdInformation 6 }

      smHardwareVpdTable OBJECT-TYPE
                    SYNTAX  SEQUENCE OF SmHardwareVpdEntry
                    ACCESS  not-accessible
                    STATUS  deprecated
                    DESCRIPTION
                    "Table of the switch module hardware components.
                    For consistent results, view as a table and not as
                    individual entries."
                    ::= { smHardwareVpd 1 }

      smHardwareVpdEntry OBJECT-TYPE
                    SYNTAX SmHardwareVpdEntry
                    ACCESS  not-accessible
                    STATUS  deprecated
                    DESCRIPTION
                    "Switch module hardware VPD entry.
                    For consistent results, view as a table and
                    not as individual entries."
                    INDEX { smHardwareVpdIndex }
                    ::= { smHardwareVpdTable 1 }

      SmHardwareVpdEntry ::= SEQUENCE {
                  smHardwareVpdIndex INTEGER,
                  smHardwareVpdBayNumber OCTET STRING,
                  smHardwareVpdManufacturingId OCTET STRING,
                  smHardwareVpdFruNumber OCTET STRING,
                  smHardwareVpdHardwareRevision INTEGER,
                  smHardwareVpdUuid OCTET STRING,
                  smHardwareVpdManufDate OCTET STRING,
                  smHardwareVpdPartNumber OCTET STRING,
                  smHardwareVpdFruSerial OCTET STRING,
                  smHardwareVpdManufacturingIDNumber OCTET STRING,
                  smHardwareVpdProductId OCTET STRING,
                  smHardwareVpdSubManufacturerId OCTET STRING,
                  smHardwareVpdClei OCTET STRING,
                  smHardwareVpdWwnGuid OCTET STRING,
                  smHardwareVpdWwnGuidType OCTET STRING,
                  smHardwareVpdWidth INTEGER,
                  smHardwareVpdHardwareRevisionString OCTET STRING
                  }

      smHardwareVpdIndex  OBJECT-TYPE
                  SYNTAX  INTEGER
                  ACCESS  read-only
                  STATUS  deprecated
                  DESCRIPTION
                  "Switch module hardware VPD index.
                  For consistent results, view as a table and not as individual entries."
                  ::= { smHardwareVpdEntry 1 }

      smHardwareVpdBayNumber  OBJECT-TYPE
                  SYNTAX  OCTET STRING
                  ACCESS  read-only
                  STATUS  deprecated
                  DESCRIPTION
                  "Switch module hardware VPD Bay number.
                  For consistent results, view as a table and not as individual entries."
                  ::= { smHardwareVpdEntry 2 }

      smHardwareVpdManufacturingId  OBJECT-TYPE
                  SYNTAX  OCTET STRING
                  ACCESS  read-only
                  STATUS  deprecated
                  DESCRIPTION
                  "Switch module hardware VPD manufacturing ID.
                  For consistent results, view as a table and not as individual entries."
                  ::= { smHardwareVpdEntry 3 }


      smHardwareVpdFruNumber  OBJECT-TYPE
                  SYNTAX  OCTET STRING
                  ACCESS  read-only
                  STATUS  deprecated
                  DESCRIPTION
                  "Switch module hardware VPD FRU number.
                  For consistent results, view as a table and not as individual entries."
                  ::= { smHardwareVpdEntry 4 }

      smHardwareVpdHardwareRevision  OBJECT-TYPE
                  SYNTAX  INTEGER
                  ACCESS  read-only
                  STATUS  deprecated
                  DESCRIPTION
                  "Switch module hardware VPD hardware revision.
                  For consistent results, view as a table and not as individual entries.
                  If a hardware revision is programmed in the OEM VPD area for this component,
                  then the HardwareRevisionString version of this MIB object should be used."
                  ::= { smHardwareVpdEntry 5 }

      smHardwareVpdUuid  OBJECT-TYPE
                  SYNTAX  OCTET STRING
                  ACCESS  read-only
                  STATUS  deprecated
                  DESCRIPTION
                  "Switch module hardware VPD UUID.
                  For consistent results, view as a table and not as individual entries."
                  ::= { smHardwareVpdEntry 8 }

      smHardwareVpdManufDate  OBJECT-TYPE
                  SYNTAX  OCTET STRING
                  ACCESS  read-only
                  STATUS  deprecated
                  DESCRIPTION
                  "Switch module hardware VPD manufacture date.
                  For consistent results, view as a table and not as individual entries."
                  ::= { smHardwareVpdEntry 9 }

      smHardwareVpdPartNumber  OBJECT-TYPE
                  SYNTAX  OCTET STRING
                  ACCESS  read-only
                  STATUS  deprecated
                  DESCRIPTION
                  "Switch module hardware VPD Part Number.
                  For consistent results, view as a table and not as individual entries."
                  ::= { smHardwareVpdEntry 10 }

      smHardwareVpdFruSerial  OBJECT-TYPE
                  SYNTAX  OCTET STRING
                  ACCESS  read-only
                  STATUS  deprecated
                  DESCRIPTION
                  "Switch module hardware VPD FRU Serial.
                  For consistent results, view as a table and not as individual entries."
                  ::= { smHardwareVpdEntry 11 }

      smHardwareVpdManufacturingIDNumber  OBJECT-TYPE
                  SYNTAX  OCTET STRING
                  ACCESS  read-only
                  STATUS  deprecated
                  DESCRIPTION
                  "Switch module hardware VPD manufacturer ID.
                  For consistent results, view as a table and not as individual entries."
                  ::= { smHardwareVpdEntry 12 }

      smHardwareVpdProductId  OBJECT-TYPE
                  SYNTAX  OCTET STRING
                  ACCESS  read-only
                  STATUS  deprecated
                  DESCRIPTION
                  "Switch module hardware VPD product ID.
                  For consistent results, view as a table and not as individual entries."
                  ::= { smHardwareVpdEntry 13 }

      smHardwareVpdSubManufacturerId  OBJECT-TYPE
                  SYNTAX  OCTET STRING
                  ACCESS  read-only
                  STATUS  deprecated
                  DESCRIPTION
                  "Switch module hardware VPD subsystem manufacturer ID.
                  For consistent results, view as a table and not as individual entries."
                  ::= { smHardwareVpdEntry 14 }

      smHardwareVpdClei  OBJECT-TYPE
                  SYNTAX  OCTET STRING
                  ACCESS  read-only
                  STATUS  deprecated
                  DESCRIPTION
                  "Switch module hardware VPD Common Language Equipment Identifier (CLEI).
                  For consistent results, view as a table and not as individual entries."
                  ::= { smHardwareVpdEntry 15 }

      smHardwareVpdWwnGuid  OBJECT-TYPE
                  SYNTAX  OCTET STRING
                  ACCESS  read-only
                  STATUS  deprecated
                  DESCRIPTION
                  "Switch module hardware VPD World Wide Name or Global Unique ID.
                  For consistent results, view as a table and not as individual entries."
                  ::= { smHardwareVpdEntry 16 }

      smHardwareVpdWwnGuidType  OBJECT-TYPE
                  SYNTAX  OCTET STRING
                  ACCESS  read-only
                  STATUS  deprecated
                  DESCRIPTION
                  "The WWN/GUID/SAS entry is actually World Wide Name, Global Unique ID
                  or Serial Attach SCSI ID.
                  For consistent results, view as a table and not as individual entries."
                  ::= { smHardwareVpdEntry 17 }

      smHardwareVpdWidth OBJECT-TYPE
                  SYNTAX  INTEGER
                  ACCESS  read-only
                  STATUS  deprecated
                  DESCRIPTION
                  "The width of the switch module hardware.
                  For consistent results, view as a table and not as individual entries."
                  ::= { smHardwareVpdEntry 18 }

      smHardwareVpdHardwareRevisionString  OBJECT-TYPE
                  SYNTAX  OCTET STRING
                  ACCESS  read-only
                  STATUS  deprecated
                  DESCRIPTION
                  "Switch module hardware VPD hardware revision in string format.
                  For consistent results, view as a table and not as individual entries.
                  If a hardware revision is programmed in the OEM VPD area for this component,
                  then this MIB object should be used."
                  ::= { smHardwareVpdEntry 20 }


       -- ********************************************************************************
       -- Switch module firmware VPD
       -- ********************************************************************************
       smFirmwareVpd OBJECT IDENTIFIER ::= { vpdInformation 7 }

       -- ********************************************************************************
       -- Switch module main application firmware VPD
       -- ********************************************************************************
         smMainAppVpdTable OBJECT-TYPE
                     SYNTAX  SEQUENCE OF SmMainAppVpdEntry
                     ACCESS  not-accessible
                     STATUS  deprecated
                     DESCRIPTION
                     "Switch module main application VPD information table."
                     ::= {smFirmwareVpd 1}

          smMainAppVpdEntry  OBJECT-TYPE
                        SYNTAX SmMainAppVpdEntry
                        ACCESS  not-accessible
                        STATUS  deprecated
                        DESCRIPTION
                        "Switch module main application VPD table entry"
                        INDEX { smMainAppVpdIndex }
                        ::= { smMainAppVpdTable 1 }

          SmMainAppVpdEntry ::= SEQUENCE {
                      smMainAppVpdIndex INTEGER,
                      smMainAppVpdId INTEGER,
                      smMainAppVpdExists INTEGER,
                      smMainAppVpdSwitchType INTEGER,
                      smMainApp1VpdBuildId OCTET STRING,
                      smMainApp1VpdBuildDate OCTET STRING,
                      smMainApp1VpdRevisionNumber OCTET STRING,
                      smMainApp2VpdBuildId OCTET STRING,
                      smMainApp2VpdBuildDate OCTET STRING,
                      smMainApp2VpdRevisionNumber OCTET STRING,
                      smMainApp3VpdBuildId OCTET STRING,
                      smMainApp3VpdBuildDate OCTET STRING,
                      smMainApp3VpdRevisionNumber OCTET STRING,
                      smMainAppVpdSwitchSubType INTEGER
                      }

          smMainAppVpdIndex OBJECT-TYPE
                      SYNTAX  INTEGER
                      ACCESS  read-only
                      STATUS  deprecated
                      DESCRIPTION
                      "Switch module main application VPD entry index."
                      ::= { smMainAppVpdEntry 1 }

          smMainAppVpdId OBJECT-TYPE
                      SYNTAX  INTEGER {
                        module1(1),
                        module2(2),
                        module3(3),
                        module4(4),
                        module5(5),
                        module6(6),
                        module7(7),
                        module8(8),
                        module9(9),
                        module10(10)
                      }
                      ACCESS  read-only
                      STATUS  deprecated
                      DESCRIPTION
                      "The switch module numeric identifier."
                      ::= { smMainAppVpdEntry 2 }

          smMainAppVpdExists OBJECT-TYPE
                      SYNTAX  INTEGER {
                        false(0),
                        true(1)
                      }
                      ACCESS  read-only
                      STATUS  deprecated
                      DESCRIPTION
                      "Indicates whether the switch module specified exists or not."
                      ::= { smMainAppVpdEntry 3 }

          smMainAppVpdSwitchType OBJECT-TYPE
                      SYNTAX  INTEGER {
                        unknown(0),
                        ethernet(1),
                        fibre(2),
                        opm(3),
                        serialCM(4),
                        copperPassThrough(5),
                        infiniband(6),
                        highSpeed(20),
                        passThrough(30),
                        sas(40)
                      }
                      ACCESS  read-only
                      STATUS  deprecated
                      DESCRIPTION
                      "Indicates the type of switch module installed."
                      ::= { smMainAppVpdEntry 4 }

          smMainApp1VpdBuildId OBJECT-TYPE
                        SYNTAX  OCTET STRING
                        ACCESS  read-only
                        STATUS  deprecated
                        DESCRIPTION
                        "Switch module firmware build id."
                        ::= { smMainAppVpdEntry 5 }

          smMainApp1VpdBuildDate OBJECT-TYPE
                        SYNTAX  OCTET STRING
                        ACCESS  read-only
                        STATUS  deprecated
                        DESCRIPTION
                        "Switch module firmware build date."
                        ::= { smMainAppVpdEntry 6 }

          smMainApp1VpdRevisionNumber OBJECT-TYPE
                        SYNTAX  OCTET STRING
                        ACCESS  read-only
                        STATUS  deprecated
                        DESCRIPTION
                        "Switch module firmware revision number."
                        ::= { smMainAppVpdEntry 7 }

          smMainApp2VpdBuildId OBJECT-TYPE
                        SYNTAX  OCTET STRING
                        ACCESS  read-only
                        STATUS  deprecated
                        DESCRIPTION
                        "Switch module firmware build id."
                        ::= { smMainAppVpdEntry 8 }

          smMainApp2VpdBuildDate OBJECT-TYPE
                        SYNTAX  OCTET STRING
                        ACCESS  read-only
                        STATUS  deprecated
                        DESCRIPTION
                        "Switch module firmware build date."
                        ::= { smMainAppVpdEntry 9 }

          smMainApp2VpdRevisionNumber OBJECT-TYPE
                        SYNTAX  OCTET STRING
                        ACCESS  read-only
                        STATUS  deprecated
                        DESCRIPTION
                        "Switch module firmware revision number."
                        ::= { smMainAppVpdEntry 10 }
          smMainApp3VpdBuildId OBJECT-TYPE
                        SYNTAX  OCTET STRING
                        ACCESS  read-only
                        STATUS  deprecated
                        DESCRIPTION
                        "I/O Module firmware build id."
                        ::= { smMainAppVpdEntry 11 }

          smMainApp3VpdBuildDate OBJECT-TYPE
                        SYNTAX  OCTET STRING
                        ACCESS  read-only
                        STATUS  deprecated
                        DESCRIPTION
                        "I/O Module firmware build date."
                        ::= { smMainAppVpdEntry 12 }

          smMainApp3VpdRevisionNumber OBJECT-TYPE
                        SYNTAX  OCTET STRING
                        ACCESS  read-only
                        STATUS  deprecated
                        DESCRIPTION
                        "I/O Module firmware revision number."
                        ::= { smMainAppVpdEntry 13 }

          smMainAppVpdSwitchSubType OBJECT-TYPE
                        SYNTAX  INTEGER {
                        unknown(0),
                        ethernet(1),
                        fibre(2),
                        infiniband(6),
                        sas(7),
                        raidsas(8),
                        icpm(9)
                      }
                      ACCESS  read-only
                      STATUS  deprecated
                      DESCRIPTION
                      "Indicates the subtype of switch module installed."
                      ::= { smMainAppVpdEntry 20 }

       -- ********************************************************************************
       -- Switch module boot ROM firmware VPD
       -- ********************************************************************************
         smBootRomVpdTable OBJECT-TYPE
                     SYNTAX  SEQUENCE OF SmBootRomVpdEntry
                     ACCESS  not-accessible
                     STATUS  deprecated
                     DESCRIPTION
                     "Switch module boot ROM VPD information table."
                     ::= {smFirmwareVpd 2}

          smBootRomVpdEntry  OBJECT-TYPE
                        SYNTAX SmBootRomVpdEntry
                        ACCESS  not-accessible
                        STATUS  deprecated
                        DESCRIPTION
                        "Switch module boot ROM VPD table entry"
                        INDEX { smBootRomVpdIndex }
                        ::= { smBootRomVpdTable 1 }

          SmBootRomVpdEntry ::= SEQUENCE {
                      smBootRomVpdIndex INTEGER,
                      smBootRomVpdId INTEGER,
                      smBootRomVpdExists INTEGER,
                      smBootRomVpdSwitchType INTEGER,
                      smBootRomVpdBuildId OCTET STRING,
                      smBootRomVpdBuildDate OCTET STRING,
                      smBootRomVpdRevisionNumber OCTET STRING,
                      smBootRomVpdSwitchSubType INTEGER
                      }

          smBootRomVpdIndex OBJECT-TYPE
                      SYNTAX  INTEGER
                      ACCESS  read-only
                      STATUS  deprecated
                      DESCRIPTION
                      "Switch module boot ROM VPD entry index."
                      ::= { smBootRomVpdEntry 1 }

          smBootRomVpdId OBJECT-TYPE
                      SYNTAX  INTEGER {
                        module1(1),
                        module2(2),
                        module3(3),
                        module4(4),
                        module5(5),
                        module6(6),
                        module7(7),
                        module8(8),
                        module9(9),
                        module10(10)
                      }
                      ACCESS  read-only
                      STATUS  deprecated
                      DESCRIPTION
                      "The switch module numeric identifier."
                      ::= { smBootRomVpdEntry 2 }

          smBootRomVpdExists OBJECT-TYPE
                      SYNTAX  INTEGER {
                        false(0),
                        true(1)
                      }
                      ACCESS  read-only
                      STATUS  deprecated
                      DESCRIPTION
                      "Indicates whether the switch module specified exists or not."
                      ::= { smBootRomVpdEntry 3 }

          smBootRomVpdSwitchType OBJECT-TYPE
                      SYNTAX  INTEGER {
                        unknown(0),
                        ethernet(1),
                        fibre(2),
                        opm(3),
                        serialCM(4),
                        copperPassThrough(5),
                        infiniband(6),
                        highSpeed(20),
                        passThrough(30),
                        sas(40)
                      }
                      ACCESS  read-only
                      STATUS  deprecated
                      DESCRIPTION
                      "Indicates the type of switch module installed."
                      ::= { smBootRomVpdEntry 4 }

          smBootRomVpdBuildId OBJECT-TYPE
                        SYNTAX  OCTET STRING
                        ACCESS  read-only
                        STATUS  deprecated
                        DESCRIPTION
                        "Switch module firmware build ID."
                        ::= { smBootRomVpdEntry 5 }

          smBootRomVpdBuildDate OBJECT-TYPE
                        SYNTAX  OCTET STRING
                        ACCESS  read-only
                        STATUS  deprecated
                        DESCRIPTION
                        "Switch module firmware build date."
                        ::= { smBootRomVpdEntry 6 }

          smBootRomVpdRevisionNumber OBJECT-TYPE
                        SYNTAX  OCTET STRING
                        ACCESS  read-only
                        STATUS  deprecated
                        DESCRIPTION
                        "Switch module firmware revision number."
                        ::= { smBootRomVpdEntry 7 }

          smBootRomVpdSwitchSubType OBJECT-TYPE
                      SYNTAX  INTEGER {
                        unknown(0),
                        ethernet(1),
                        fibre(2),
                        infiniband(6),
                        sas(7),
                        raidsas(8),
                        icpm(9)
                      }
                      ACCESS  read-only
                      STATUS  deprecated
                      DESCRIPTION
                      "Indicates the subtype of switch module installed."
                      ::= { smBootRomVpdEntry 8 }

      -- ********************************************************************************
      -- Power Module Hardware VPD
      -- ********************************************************************************
      pmHardwareVpd OBJECT IDENTIFIER ::= { vpdInformation 8 }

      pmHardwareVpdTable OBJECT-TYPE
                    SYNTAX  SEQUENCE OF PmHardwareVpdEntry
                    ACCESS  not-accessible
                    STATUS  deprecated
                    DESCRIPTION
                    "Table of the power module hardware components.
                    For consistent results, view as a table and not as individual entries."
                    ::= { pmHardwareVpd 1 }

      pmHardwareVpdEntry OBJECT-TYPE
                    SYNTAX PmHardwareVpdEntry
                    ACCESS  not-accessible
                    STATUS  deprecated
                    DESCRIPTION
                    "Power module hardware VPD entry.
                    For consistent results, view as a table and not as individual entries."
                    INDEX { pmHardwareVpdIndex }
                    ::= { pmHardwareVpdTable 1 }

      PmHardwareVpdEntry ::= SEQUENCE {
                  pmHardwareVpdIndex INTEGER,
                  pmHardwareVpdBayNumber OCTET STRING,
                  pmHardwareVpdManufacturingId OCTET STRING,
                  pmHardwareVpdFruNumber OCTET STRING,
                  pmHardwareVpdHardwareRevision INTEGER,
                  pmHardwareVpdUuid OCTET STRING,
                  pmHardwareVpdManufDate OCTET STRING,
                  pmHardwareVpdPartNumber OCTET STRING,
                  pmHardwareVpdFruSerial OCTET STRING,
                  pmHardwareVpdManufacturingIDNumber OCTET STRING,
                  pmHardwareVpdProductId OCTET STRING,
                  pmHardwareVpdSubManufacturerId OCTET STRING,
                  pmHardwareVpdClei OCTET STRING,
                  pmHardwareVpdHardwareRevisionString OCTET STRING
                  }

      pmHardwareVpdIndex  OBJECT-TYPE
                  SYNTAX  INTEGER
                  ACCESS  read-only
                  STATUS  deprecated
                  DESCRIPTION
                  "Power module hardware VPD index.
                  For consistent results, view as a table and not as individual entries."
                  ::= { pmHardwareVpdEntry 1 }

      pmHardwareVpdBayNumber  OBJECT-TYPE
                  SYNTAX  OCTET STRING
                  ACCESS  read-only
                  STATUS  deprecated
                  DESCRIPTION
                  "Power module hardware VPD Bay number.
                  For consistent results, view as a table and not as individual entries."
                  ::= { pmHardwareVpdEntry 2 }

      pmHardwareVpdManufacturingId  OBJECT-TYPE
                  SYNTAX  OCTET STRING
                  ACCESS  read-only
                  STATUS  deprecated
                  DESCRIPTION
                  "Power module hardware VPD manufacturing ID.
                  For consistent results, view as a table and not as individual entries."
                  ::= { pmHardwareVpdEntry 3 }

      pmHardwareVpdFruNumber  OBJECT-TYPE
                  SYNTAX  OCTET STRING
                  ACCESS  read-only
                  STATUS  deprecated
                  DESCRIPTION
                  "Power module hardware VPD FRU number.
                  For consistent results, view as a table and not as individual entries."
                  ::= { pmHardwareVpdEntry 4 }

      pmHardwareVpdHardwareRevision  OBJECT-TYPE
                  SYNTAX  INTEGER
                  ACCESS  read-only
                  STATUS  deprecated
                  DESCRIPTION
                  "Power module hardware VPD hardware revision.
                  For consistent results, view as a table and not as individual entries.
                  If a hardware revision is programmed in the OEM VPD area for this component,
                  then the HardwareRevisionString version of this MIB object should be used."
                  ::= { pmHardwareVpdEntry 5 }

      pmHardwareVpdUuid  OBJECT-TYPE
                  SYNTAX  OCTET STRING
                  ACCESS  read-only
                  STATUS  deprecated
                  DESCRIPTION
                  "Power module hardware VPD UUID.
                  For consistent results, view as a table and not as individual entries."
                  ::= { pmHardwareVpdEntry 8 }

      pmHardwareVpdManufDate  OBJECT-TYPE
                  SYNTAX  OCTET STRING
                  ACCESS  read-only
                  STATUS  deprecated
                  DESCRIPTION
                  "Power module hardware VPD Manufacture Date.
                  For consistent results, view as a table and not as individual entries."
                  ::= { pmHardwareVpdEntry 9 }

      pmHardwareVpdPartNumber  OBJECT-TYPE
                  SYNTAX  OCTET STRING
                  ACCESS  read-only
                  STATUS  deprecated
                  DESCRIPTION
                  "Power module hardware VPD Part Number.
                  For consistent results, view as a table and not as individual entries."
                  ::= { pmHardwareVpdEntry 10 }

      pmHardwareVpdFruSerial  OBJECT-TYPE
                  SYNTAX  OCTET STRING
                  ACCESS  read-only
                  STATUS  deprecated
                  DESCRIPTION
                  "Power module hardware VPD FRU Serial.
                  For consistent results, view as a table and not as individual entries."
                  ::= { pmHardwareVpdEntry 11 }

      pmHardwareVpdManufacturingIDNumber  OBJECT-TYPE
                  SYNTAX  OCTET STRING
                  ACCESS  read-only
                  STATUS  deprecated
                  DESCRIPTION
                  "Power module hardware VPD manufacturer ID.
                  For consistent results, view as a table and not as individual entries."
                  ::= { pmHardwareVpdEntry 12 }

      pmHardwareVpdProductId  OBJECT-TYPE
                  SYNTAX  OCTET STRING
                  ACCESS  read-only
                  STATUS  deprecated
                  DESCRIPTION
                  "Power module hardware VPD product ID.
                  For consistent results, view as a table and not as individual entries."
                  ::= { pmHardwareVpdEntry 13 }

      pmHardwareVpdSubManufacturerId  OBJECT-TYPE
                  SYNTAX  OCTET STRING
                  ACCESS  read-only
                  STATUS  deprecated
                  DESCRIPTION
                  "Power module hardware VPD subsystem manufacturer ID.
                  For consistent results, view as a table and not as individual entries."
                  ::= { pmHardwareVpdEntry 14 }

      pmHardwareVpdClei  OBJECT-TYPE
                  SYNTAX  OCTET STRING
                  ACCESS  read-only
                  STATUS  deprecated
                  DESCRIPTION
                  "Power module hardware VPD Common Language Equipment Identifier (CLEI).
                  For consistent results, view as a table and not as individual entries."
                  ::= { pmHardwareVpdEntry 15 }

      pmHardwareVpdHardwareRevisionString  OBJECT-TYPE
                  SYNTAX  OCTET STRING
                  ACCESS  read-only
                  STATUS  deprecated
                  DESCRIPTION
                  "Power module hardware VPD hardware revision in string format.
                  For consistent results, view as a table and not as individual entries.
                  If a hardware revision is programmed in the OEM VPD area for this component,
                  then this MIB object should be used."
                  ::= { pmHardwareVpdEntry 16 }

      -- ********************************************************************************
      -- Rear LED Card Hardware VPD   (was Media Tray)
      -- ********************************************************************************
      rearLEDCardHardwareVpd OBJECT IDENTIFIER ::= { vpdInformation 9 }

      rearLEDCardHardwareVpdManufacturingId  OBJECT-TYPE
                  SYNTAX  OCTET STRING
                  ACCESS  read-only
                  STATUS  deprecated
                  DESCRIPTION
                  "Rear LED card hardware VPD manufacturing ID.
                  For consistent results, view as a table and not as individual entries."
                  ::= { rearLEDCardHardwareVpd 3 }

      rearLEDCardHardwareVpdFruNumber  OBJECT-TYPE
                  SYNTAX  OCTET STRING
                  ACCESS  read-only
                  STATUS  deprecated
                  DESCRIPTION
                  "Rear LED card hardware VPD FRU number.
                  For consistent results, view as a table and not as individual entries."
                  ::= { rearLEDCardHardwareVpd 4 }

      rearLEDCardHardwareVpdHardwareRevision  OBJECT-TYPE
                  SYNTAX  INTEGER
                  ACCESS  read-only
                  STATUS  deprecated
                  DESCRIPTION
                  "Rear LED card hardware VPD hardware revision.
                  For consistent results, view as a table and not as individual entries.
                  If a hardware revision is programmed in the OEM VPD area for this component,
                  then the HardwareRevisionString version of this MIB object should be used."
                  ::= { rearLEDCardHardwareVpd 5 }

      rearLEDCardHardwareVpdUuid  OBJECT-TYPE
                  SYNTAX  OCTET STRING
                  ACCESS  read-only
                  STATUS  deprecated
                  DESCRIPTION
                  "Rear LED card hardware VPD UUID.
                  For consistent results, view as a table and not as individual entries."
                  ::= { rearLEDCardHardwareVpd 8 }

      rearLEDCardHardwareVpdManufacturingIDNumber  OBJECT-TYPE
                  SYNTAX  OCTET STRING
                  ACCESS  read-only
                  STATUS  deprecated
                  DESCRIPTION
                  "Rear LED card hardware VPD manufacturer ID.
                  For consistent results, view as a table and not as individual entries."
                  ::= { rearLEDCardHardwareVpd 9 }

      rearLEDCardHardwareVpdProductId  OBJECT-TYPE
                  SYNTAX  OCTET STRING
                  ACCESS  read-only
                  STATUS  deprecated
                  DESCRIPTION
                  "Rear LED card hardware VPD product ID.
                  For consistent results, view as a table and not as individual entries."
                  ::= { rearLEDCardHardwareVpd 10 }

      rearLEDCardHardwareVpdSubManufacturerId  OBJECT-TYPE
                  SYNTAX  OCTET STRING
                  ACCESS  read-only
                  STATUS  deprecated
                  DESCRIPTION
                  "Rear LED card hardware VPD subsystem manufacturer ID.
                  For consistent results, view as a table and not as individual entries."
                  ::= { rearLEDCardHardwareVpd 11 }

      rearLEDCardHardwareVpdClei  OBJECT-TYPE
                  SYNTAX  OCTET STRING
                  ACCESS  read-only
                  STATUS  deprecated
                  DESCRIPTION
                  "Rear LED card hardware VPD Common Language Equipment Identifier (CLEI).
                  For consistent results, view as a table and not as individual entries."
                  ::= { rearLEDCardHardwareVpd 12 }

      rearLEDCardHardwareVpdHardwareRevisionString  OBJECT-TYPE
                  SYNTAX  OCTET STRING
                  ACCESS  read-only
                  STATUS  deprecated
                  DESCRIPTION
                  "Rear LED card hardware VPD hardware revision in string format.
                  For consistent results, view as a table and not as individual entries.
                  If a hardware revision is programmed in the OEM VPD area for this component,
                  then this  MIB object should be used."
                  ::= { rearLEDCardHardwareVpd 17 }

      rearLEDCardHardwareVpdManufDate  OBJECT-TYPE
                  SYNTAX  OCTET STRING
                  ACCESS  read-only
                  STATUS  deprecated
                  DESCRIPTION
                  "Rear LED card hardware VPD Manufacture Date."
                  ::= { rearLEDCardHardwareVpd 18 }

      rearLEDCardHardwareVpdPartNumber  OBJECT-TYPE
                  SYNTAX  OCTET STRING
                  ACCESS  read-only
                  STATUS  deprecated
                  DESCRIPTION
                  "Rear LED card hardware VPD Part Number."
                  ::= { rearLEDCardHardwareVpd 19 }

      rearLEDCardHardwareVpdFruSerial  OBJECT-TYPE
                  SYNTAX  OCTET STRING
                  ACCESS  read-only
                  STATUS  deprecated
                  DESCRIPTION
                  "Rear LED card hardware VPD FRU Serial."
                  ::= { rearLEDCardHardwareVpd 20 }

      -- ********************************************************************************
      -- Chassis fan firmware level VPD
      -- ********************************************************************************
      chassisFanFirmwareVpd OBJECT IDENTIFIER ::= { vpdInformation 12 }

       chassisFanControllerVPDTable OBJECT-TYPE
                      SYNTAX  SEQUENCE OF ChassisFanControllerVPDEntry
                      ACCESS  not-accessible
                      STATUS  deprecated
                      DESCRIPTION
                      "Table of chassis fan controller firmware vital product data (VPD) information."
                      ::= { chassisFanFirmwareVpd 1 }

        chassisFanControllerVPDEntry OBJECT-TYPE
                      SYNTAX ChassisFanControllerVPDEntry
                      ACCESS  not-accessible
                      STATUS  deprecated
                      DESCRIPTION
                      "Chassis fan controller firmware VPD table entry"
                      INDEX { chassisFanControllerVpdIndex }
                      ::= { chassisFanControllerVPDTable 1 }

        ChassisFanControllerVPDEntry ::= SEQUENCE {
                    chassisFanControllerVpdIndex INTEGER,
                    chassisFanControllerVpdId INTEGER,
                    chassisFanControllerVpdExists INTEGER,
                    chassisFanControllerVpdRevision OCTET STRING
                    }

        chassisFanControllerVpdIndex  OBJECT-TYPE
                    SYNTAX  INTEGER
                    ACCESS  read-only
                    STATUS  deprecated
                    DESCRIPTION
                    "Chassis fan controller firmware VPD table index."
                    ::= { chassisFanControllerVPDEntry 1 }


        chassisFanControllerVpdId  OBJECT-TYPE
                    SYNTAX  INTEGER {
                      chassisFan1(1),
                      chassisFan2(2),
                      chassisFan3(3),
                      chassisFan4(4),
                      chassisFan5(5),
                      chassisFan6(6),
                      chassisFan7(7),
                      chassisFan8(8),
                      chassisFan9(9),
                      chassisFan10(10)
                    }
                    ACCESS  read-only
                    STATUS  deprecated
                    DESCRIPTION
                    "The numeric chassis fan ID."
                    ::= { chassisFanControllerVPDEntry 2 }

        chassisFanControllerVpdExists OBJECT-TYPE
                    SYNTAX  INTEGER {
                      false(0),
                      true(1)
                    }
                    ACCESS  read-only
                    STATUS  deprecated
                    DESCRIPTION
                    "Indicates whether the chassis fan specified exists or not."
                    ::= { chassisFanControllerVPDEntry 3 }

        chassisFanControllerVpdRevision OBJECT-TYPE
                    SYNTAX  OCTET STRING
                    ACCESS  read-only
                    STATUS  deprecated
                    DESCRIPTION
                    "The revision of the chassis fan controller firmware."
                    ::= { chassisFanControllerVPDEntry 7 }

      -- ********************************************************************************
      -- Chassis fan hardware VPD
      -- ********************************************************************************
      chassisFanHardwareVpd OBJECT IDENTIFIER ::= { vpdInformation 13 }

      chassisFanHardwareVpdTable OBJECT-TYPE
                    SYNTAX  SEQUENCE OF ChassisFanHardwareVpdEntry
                    ACCESS  not-accessible
                    STATUS  deprecated
                    DESCRIPTION
                    "Table of the chassis fan hardware components."
                    ::= { chassisFanHardwareVpd 1 }

      chassisFanHardwareVpdEntry OBJECT-TYPE
                    SYNTAX ChassisFanHardwareVpdEntry
                    ACCESS  not-accessible
                    STATUS  deprecated
                    DESCRIPTION
                    "Chassis fan hardware VPD entry."
                    INDEX { chassisFanHardwareVpdIndex }
                    ::= { chassisFanHardwareVpdTable 1 }

      ChassisFanHardwareVpdEntry ::= SEQUENCE {
                  chassisFanHardwareVpdIndex INTEGER,
                  chassisFanHardwareVpdBayNumber OCTET STRING,
                  chassisFanHardwareVpdManufacturingId OCTET STRING,
                  chassisFanHardwareVpdFruNumber OCTET STRING,
                  chassisFanHardwareVpdHardwareRevision INTEGER,
                  chassisFanHardwareVpdUuid OCTET STRING,
                  chassisFanHardwareVpdManufDate OCTET STRING,
                  chassisFanHardwareVpdPartNumber OCTET STRING,
                  chassisFanHardwareVpdFruSerial OCTET STRING,
                  chassisFanHardwareVpdManufacturingIDNumber OCTET STRING,
                  chassisFanHardwareVpdProductId OCTET STRING,
                  chassisFanHardwareVpdSubManufacturerId OCTET STRING,
                  chassisFanHardwareVpdClei OCTET STRING,
                  chassisFanHardwareVpdHardwareRevisionString OCTET STRING
                  }

      chassisFanHardwareVpdIndex  OBJECT-TYPE
                  SYNTAX  INTEGER
                  ACCESS  read-only
                  STATUS  deprecated
                  DESCRIPTION
                  "Chassis fan hardware VPD index."
                  ::= { chassisFanHardwareVpdEntry 1 }

      chassisFanHardwareVpdBayNumber  OBJECT-TYPE
                  SYNTAX  OCTET STRING
                  ACCESS  read-only
                  STATUS  deprecated
                  DESCRIPTION
                  "Chassis fan hardware VPD Bay number."
                  ::= { chassisFanHardwareVpdEntry 2 }

      chassisFanHardwareVpdManufacturingId  OBJECT-TYPE
                  SYNTAX  OCTET STRING
                  ACCESS  read-only
                  STATUS  deprecated
                  DESCRIPTION
                  "Chassis fan hardware VPD manufacturing ID."
                  ::= { chassisFanHardwareVpdEntry 3 }

      chassisFanHardwareVpdFruNumber  OBJECT-TYPE
                  SYNTAX  OCTET STRING
                  ACCESS  read-only
                  STATUS  deprecated
                  DESCRIPTION
                  "Chassis fan hardware VPD FRU number."
                  ::= { chassisFanHardwareVpdEntry 4 }

      chassisFanHardwareVpdHardwareRevision  OBJECT-TYPE
                  SYNTAX  INTEGER
                  ACCESS  read-only
                  STATUS  deprecated
                  DESCRIPTION
                  "Chassis fan hardware VPD hardware revision."
                  ::= { chassisFanHardwareVpdEntry 5 }

      chassisFanHardwareVpdUuid  OBJECT-TYPE
                  SYNTAX  OCTET STRING
                  ACCESS  read-only
                  STATUS  deprecated
                  DESCRIPTION
                  "Chassis fan hardware VPD UUID."
                  ::= { chassisFanHardwareVpdEntry 8 }

      chassisFanHardwareVpdManufDate  OBJECT-TYPE
                  SYNTAX  OCTET STRING
                  ACCESS  read-only
                  STATUS  deprecated
                  DESCRIPTION
                  "Chassis fan hardware VPD manufacture Date."
                  ::= { chassisFanHardwareVpdEntry 9 }

      chassisFanHardwareVpdPartNumber  OBJECT-TYPE
                  SYNTAX  OCTET STRING
                  ACCESS  read-only
                  STATUS  deprecated
                  DESCRIPTION
                  "Chassis fan hardware VPD Part Number."
                  ::= { chassisFanHardwareVpdEntry 10 }

      chassisFanHardwareVpdFruSerial  OBJECT-TYPE
                  SYNTAX  OCTET STRING
                  ACCESS  read-only
                  STATUS  deprecated
                  DESCRIPTION
                  "Chassis fan hardware VPD FRU serial number."
                  ::= { chassisFanHardwareVpdEntry 11 }

      chassisFanHardwareVpdManufacturingIDNumber  OBJECT-TYPE
                  SYNTAX  OCTET STRING
                  ACCESS  read-only
                  STATUS  deprecated
                  DESCRIPTION
                  "Chassis fan hardware VPD manufacturer ID."
                  ::= { chassisFanHardwareVpdEntry 12 }

      chassisFanHardwareVpdProductId  OBJECT-TYPE
                  SYNTAX  OCTET STRING
                  ACCESS  read-only
                  STATUS  deprecated
                  DESCRIPTION
                  "Chassis fan hardware VPD product ID."
                  ::= { chassisFanHardwareVpdEntry 13 }

      chassisFanHardwareVpdSubManufacturerId  OBJECT-TYPE
                  SYNTAX  OCTET STRING
                  ACCESS  read-only
                  STATUS  deprecated
                  DESCRIPTION
                  "Chassis fan hardware VPD subsystem manufacturer ID."
                  ::= { chassisFanHardwareVpdEntry 14 }

      chassisFanHardwareVpdClei  OBJECT-TYPE
                  SYNTAX  OCTET STRING
                  ACCESS  read-only
                  STATUS  deprecated
                  DESCRIPTION
                  "Chassis fan hardware VPD Common Language Equipment Identifier (CLEI)."
                  ::= { chassisFanHardwareVpdEntry 15 }

      chassisFanHardwareVpdHardwareRevisionString  OBJECT-TYPE
                  SYNTAX  OCTET STRING
                  ACCESS  read-only
                  STATUS  deprecated
                  DESCRIPTION
                  "Chassis fan hardware VPD hardware revision in string format."
                  ::= { chassisFanHardwareVpdEntry 16 }

      -- ********************************************************************************
      -- Power Module Firmware Level VPD
      -- ********************************************************************************
      pmFirmwareVpd OBJECT IDENTIFIER ::= { vpdInformation 14 }

       pmControllerVPDTable OBJECT-TYPE
                      SYNTAX  SEQUENCE OF PmControllerVPDEntry
                      ACCESS  not-accessible
                      STATUS  deprecated
                      DESCRIPTION
                      "Table of Power Module controller firmware vital product data (VPD) information."
                      ::= { pmFirmwareVpd 1 }

        pmControllerVPDEntry OBJECT-TYPE
                      SYNTAX PmControllerVPDEntry
                      ACCESS  not-accessible
                      STATUS  deprecated
                      DESCRIPTION
                      "Power Module controller firmware VPD table entry"
                      INDEX { pmControllerVpdIndex }
                      ::= { pmControllerVPDTable 1 }

        PmControllerVPDEntry ::= SEQUENCE {
                    pmControllerVpdIndex INTEGER,
                    pmControllerVpdId INTEGER,
                    pmControllerVpdExists INTEGER,
                    pmControllerVpdRevision OCTET STRING
                    }

        pmControllerVpdIndex  OBJECT-TYPE
                    SYNTAX  INTEGER
                    ACCESS  read-only
                    STATUS  deprecated
                    DESCRIPTION
                    "Power Module controller firmware VPD table index."
                    ::= { pmControllerVPDEntry 1 }

        pmControllerVpdId  OBJECT-TYPE
                    SYNTAX  INTEGER {
                      powerModule1(1),
                      powerModule2(2),
                      powerModule3(3),
                      powerModule4(4),
                      powerModule5(5),
                      powerModule6(6)
                    }
                    ACCESS  read-only
                    STATUS  deprecated
                    DESCRIPTION
                    "The numeric Power Module ID."
                    ::= { pmControllerVPDEntry 2 }

        pmControllerVpdExists OBJECT-TYPE
                    SYNTAX  INTEGER {
                      false(0),
                      true(1)
                    }
                    ACCESS  read-only
                    STATUS  deprecated
                    DESCRIPTION
                    "Indicates whether the Power Module specified exists or not."
                    ::= { pmControllerVPDEntry 3 }

        pmControllerVpdRevision OBJECT-TYPE
                    SYNTAX  OCTET STRING
                    ACCESS  read-only
                    STATUS  deprecated
                    DESCRIPTION
                    "The revision of the Power Module controller firmware."
                    ::= { pmControllerVPDEntry 7 }

      -- ********************************************************************************
      -- Reload VPD
      -- ********************************************************************************
        reloadVpdData OBJECT IDENTIFIER ::= { vpdInformation 23 }

        reloadAllVpdData OBJECT-TYPE
                    SYNTAX  INTEGER {
                        execute(1)
                    }
                    ACCESS  read-write
                    STATUS  mandatory
                    DESCRIPTION
                    "Reload all VPD data (firmware, hardware, MAC address, WWN/GUID and other Unique ID).
                    NOTE: The value returned for the GET command is meaningless."
                    ::= { reloadVpdData 1 }

        reloadFwVpdData OBJECT-TYPE
                    SYNTAX  INTEGER {
                        execute(1)
                    }
                    ACCESS  read-write
                    STATUS  mandatory
                    DESCRIPTION
                    "Reload firmware VPD data.
                    NOTE: The value returned for the GET command is meaningless."
                    ::= { reloadVpdData 2 }

        reloadHwVpdData OBJECT-TYPE
                    SYNTAX  INTEGER {
                        execute(1)
                    }
                    ACCESS  read-write
                    STATUS  mandatory
                    DESCRIPTION
                    "Reload hardware VPD data.
                    NOTE: The value returned for the GET command is meaningless."
                    ::= { reloadVpdData 3 }

        reloadMACAddress OBJECT-TYPE
                    SYNTAX  INTEGER {
                        execute(1)
                    }
                    ACCESS  read-write
                    STATUS  mandatory
                    DESCRIPTION
                    "Reload blade MAC addresses.
                    NOTE: The value returned for the GET command is meaningless."
                    ::= { reloadVpdData 4 }

        reloadWwnGuidVpdData OBJECT-TYPE
                    SYNTAX  INTEGER {
                        execute(1)
                    }
                    ACCESS  read-write
                    STATUS  mandatory
                    DESCRIPTION
                    "Reload blade and I/O module WWN/GUID and other VPD data.
                    NOTE: The value returned for the GET command is meaningless."
                    ::= { reloadVpdData 5 }

    -- *************************************************************************
    -- Passive Air Filter
    -- *************************************************************************

    airFilter  OBJECT IDENTIFIER ::= { monitors 22 }

      passiveAirFilter  OBJECT IDENTIFIER ::= { airFilter 1 }

        passiveAirFilterStatus    OBJECT-TYPE
                 SYNTAX  INTEGER {
                   disabled(0),
                   enabled(1)
                 }
                 ACCESS  read-write
                 STATUS  mandatory
                 DESCRIPTION
                 "Disable/Enable the passive air filter replacement timer."
                 ::= { passiveAirFilter 1 }

        passiveAirFilterMonthFreq    OBJECT-TYPE
                 SYNTAX  INTEGER {
                   oneMonth(1),
                   threeMonths(3),
                   sixMonths(6)
                 }
                 ACCESS  read-write
                 STATUS  mandatory
                 DESCRIPTION
                 "The chassis environment.  1 month indicates high dust, 3 months indicates 
                  moderate dust and, 6 months indicates low dust."
                 ::= { passiveAirFilter 2 }

        passiveAirFilterReplaceDate OBJECT-TYPE
                 SYNTAX  OCTET STRING (SIZE(0..30))
                 ACCESS  read-only
                 STATUS  mandatory
                 DESCRIPTION
                 "The scheduled replacement date of the air filter."
                 ::= { passiveAirFilter 3 }

      -- *************************************************************************
      -- Component Information
      --
      -- This anchor is for a new set of tables that provide information about all
      -- of the components in the chassis. For example, the componentInventoryTable
      -- provides inventory information for all components in a single table and the
      -- componentFirmwareTable provides firmware information for all components in
      -- a single table. In previously defined tables, this information was
      -- scattered about several tables, while this new concept provides a more
      -- concise presentation.
      --
      -- The objects under the componentInformation anchor replace most of the legacy
      -- objects defined under the vpdInformation anchor. Please see the block 
      -- comment at the start of that section for details. 
      --
      -- *************************************************************************

      componentInformation  OBJECT IDENTIFIER ::= { monitors 23 }

      -- *************************************************************************
      -- Component Inventory Information
      -- *************************************************************************
      componentInventory OBJECT IDENTIFIER ::= { componentInformation 1 }

      componentInventoryTable OBJECT-TYPE
                    SYNTAX  SEQUENCE OF ComponentInventoryEntry
                    ACCESS  not-accessible
                    STATUS  mandatory
                    DESCRIPTION
                    "Table of component inventory information. Not all components will
                     provide every object defined in the ComponentInventoryEntry. Also, 
                     if a component does not have inventory information or the CMM is not able
                     to read the data from the device, then there will not be a row in 
                     this table for the component."
                    ::= { componentInventory 1 }

      componentInventoryEntry OBJECT-TYPE
                    SYNTAX ComponentInventoryEntry
                    ACCESS  not-accessible
                    STATUS  mandatory
                    DESCRIPTION
                    "Component inventory information."
                    INDEX { componentInventoryTopologyPath }
                    ::= { componentInventoryTable 1 }

      ComponentInventoryEntry ::= SEQUENCE {
                  componentInventoryTopologyPath OCTET STRING,
                  componentInventoryInstance INTEGER,
                  componentInventoryDescription OCTET STRING,
                  componentInventoryMachineTypeModel OCTET STRING,
                  componentInventoryMachineSerial OCTET STRING,
                  componentInventoryAssetID OCTET STRING,
                  componentInventoryPartNumber OCTET STRING,
                  componentInventoryFRUNumber OCTET STRING,
                  componentInventoryFRUSerialNumber OCTET STRING,
                  componentInventoryManufacture OCTET STRING,
                  componentInventoryHardwareRevision OCTET STRING,
                  componentInventoryManufactureDate OCTET STRING,
                  componentInventoryUUID OCTET STRING,
                  componentInventoryProductID OCTET STRING,
                  componentInventorySubManufactureID OCTET STRING,
                  componentInventoryCLEI OCTET STRING,
                  componentInventoryAssetTag OCTET STRING,
                  componentInventorySpeed OCTET STRING,
                  componentInventoryIdentifier OCTET STRING,
                  componentInventorySize INTEGER,
                  componentInventoryMemoryType INTEGER,
                  componentInventoryProductName OCTET STRING,
                  componentInventoryProductVersion OCTET STRING,
                  componentInventoryProcessorType INTEGER,
                  componentInventoryProcessorFamily OCTET STRING,
                  componentInventoryProcessorCores OCTET STRING,
                  componentInventoryProcessorThreads OCTET STRING,
                  componentInventoryProcessorL1DCache OCTET STRING,
                  componentInventoryProcessorL1ICache OCTET STRING,
                  componentInventoryProcessorL2Cache OCTET STRING,
                  componentInventoryProcessorL3Cache OCTET STRING,
                  componentInventoryProcessorVoltage OCTET STRING,
                  componentInventoryProcessorExtClock OCTET STRING,
                  componentInventoryProcessorDataWidth OCTET STRING,
                  componentInventoryManufactureIDNum INTEGER,
                  componentInventoryGlobalID OCTET STRING
                  }

      componentInventoryTopologyPath  OBJECT-TYPE
                  SYNTAX  OCTET STRING  (SIZE (0..100))
                  ACCESS  read-only
                  STATUS  mandatory
                  DESCRIPTION
                  "The unique identifier for a row in this table. The chassis and each
                   installed component is represented by a hardware topology tree, where
                   each node in the tree represents a component. The path to a particular
                   component consists of one or more <component>,<instance> pairs, where
                   each successive pair is a child of the previous parent pair.

                   As an example, the root of the tree is the chassis and is represented
                   by the pair 'CHASSIS, 1'. This pair indicates the first instance of
                   the chassis. If a blade is inserted in slot 4 of the chassis, its
                   topology path is 'CHASSIS, 1, BLADE, 4'. With this format, the
                   components in the chassis can be determined along with their relative
                   hierarchy to each other.

                   This component inventory table is indexed by this unique topology
                   path and the numeric designations for the components are:

                    CHASSIS,                0x01   Chassis
                    MM,                     0x02   Management Module
                    BLADE,                  0x03   Main system board of a blade
                    POWER,                  0x04   Power Supply, Power Module, etc
                    COOLING,                0x05   Fan, blower, or other cooling device
                    IO_MODULE,              0x06   Has I/O interface, i.e. - switch or bridge
                    MEDIA,                  0x07   Media device
                    PROCESSOR,              0x08   Any processor, processor module, etc
                    STORAGE,                0x09   Any type of storage device
                    EXPANSION,              0x0A   Expansion Card (not covered by more specific type)
                    MEMORY,                 0x0B   Any memory device, module, etc
                    MFRU,                   0x0C   Managed FRU Device
                    PANEL,                  0x0D   Any sort of panel device, such as a front panel
                    BLADE_EXPANSION_MODULE, 0x0E   Expansion option (BEM) such as PEU, BSE, etc
                    CARD_EXPANSION,         0x0F   Expansion card, ie. daughter card
                    CARD_HS_EXPANSION,      0x10   High Speed Expansion card, ie. daughter card
                    INTERPOSER,             0x11   Interposer device
                    CLOCK,                  0x12   Clock card
                    MUX,                    0x13   Mulitplexer card
                    ADDIN,                  0x14   cKVM card & other addin cards
                    STORAGE_MODULE,         0x15   Container of one or more Storage Devices
                    SYS_EXPANSION_CARD,     0x16   Management card
                    BATTERY,                0x17   A single battery
                    BATTERY_MODULE,         0x18   Container of one or more batteries
                    REAR_LED,               0x19   Rear LED card
                    MEMORY_BANK,            0x1A   Memory banks
                    AIR_FILTER,             0x1B   Filter mechanism (bezel)
                    SERIAL_PORT_MODULE,     0x1C   Container of one or more serial ports
                    PARENT,                 0x1D   Reference to parent for multi-parent support
                    PHY_PORT,               0x1E   Physical port
                    IO_EXPANDER,            0x1F   RAID card
                    CABLE,                  0x20   Cable/Interconnect
                    FAN_MUX,                0x29   Fan multiplexer card
                     PCI_EXPRESS,            0x32   PCI express card on (PEN)
                     FLASH_DIMM,             0x33   Used for SPD devices that matches the silkscreen of the DIMM slot
                     RACK,                   0x50   Rack
                     PLATFORM,               0x51   Generic Platform like rack mounted server/appliance
                     DATAPLEX,               0x52   DataPlex
                     OTHER,                  0x53   Other unknown etc.
                     PERIPHERAL_MODULE,      0x54 
                     SYSTEM_BOARD,           0x55   System board
                     PROCESSOR_MODULE,       0x56 
                     BACK_PANEL,             0x57 
                     POWER_SYSTEM_BOARD,     0x58 
                     STORAGE_BACKPLANE,      0x59   Drive back plane
                     PROC_BOARD,             0x5A   Holds 1 or more processors
                     POWER_DI,               0x5B   Power mgt / power distribution board
                     CHASSIS_BACK_PANEL,     0x5C 
                     SUB_CHASSIS,            0x5D 
                     OTHER_CHASSIS_BOARD,    0x5E 
                     DEVICE_MODULE,          0x5F 
                     REMOTE_DEVICE,          0x60   Remote mgt communication device
                     EXTERNAL_ENVIRONMENT,   0x61   Such as external temp sensor for outside box temps
                     PROC_MEMORY_MODULE,     0x62   Processors and memory on same module"

                  ::= { componentInventoryEntry 1 }

      componentInventoryInstance  OBJECT-TYPE
                  SYNTAX  INTEGER
                  ACCESS  read-only
                  STATUS  mandatory
                  DESCRIPTION
                  "The slot number or instance of a particular component. Typically,
                   if the component plugs into the chassis, this represents the slot
                   number. However, some components are connected to another component,
                   and this represents the instance. For example, a blade may have
                   several expansion cards that connect to the blade system planar,
                   and in this case, this value identifies which expansion card
                   instance the row represents.

                   Note that this slot/instance value can be determined from the
                   componentInventoryTopologyPath object, but this
                   componentInventoryInstance object is provided as a convenience
                   to the user."
                  ::= { componentInventoryEntry 2 }

      componentInventoryDescription  OBJECT-TYPE
                  SYNTAX  OCTET STRING
                  ACCESS  read-only
                  STATUS  mandatory
                  DESCRIPTION
                  "A short text string describing the particular component.
                   If a text string is not available, a value of
                   'Not available' is presented.

                   For more detail, also refer to the componentInventoryProductName
                   object in this table or the componentXXXXName object of any of the 
                   other component tables under the 'components' section of the MIB."
                  ::= { componentInventoryEntry 3 }

      componentInventoryMachineTypeModel  OBJECT-TYPE
                  SYNTAX  OCTET STRING
                  ACCESS  read-only
                  STATUS  mandatory
                  DESCRIPTION
                  "The machine type and model number of this component. Typically,
                   the format is XXXXYYY, where XXXX reprsents the machine type
                   and YYY represents the model number."
                  ::= { componentInventoryEntry 4 }

      componentInventoryMachineSerial  OBJECT-TYPE
                  SYNTAX  OCTET STRING
                  ACCESS  read-only
                  STATUS  mandatory
                  DESCRIPTION
                  "The machine serial number of this component."
                  ::= { componentInventoryEntry 5 }

      componentInventoryAssetID  OBJECT-TYPE
                  SYNTAX  OCTET STRING
                  ACCESS  read-only
                  STATUS  mandatory
                  DESCRIPTION
                  "The asset identifier of this component, typically set by some
                   other authority than the
                   manufacturer."
                  ::= { componentInventoryEntry 6 }

      componentInventoryPartNumber  OBJECT-TYPE
                  SYNTAX  OCTET STRING
                  ACCESS  read-only
                  STATUS  mandatory
                  DESCRIPTION
                  "The part number of this component."
                  ::= { componentInventoryEntry 7 }

      componentInventoryFRUNumber  OBJECT-TYPE
                  SYNTAX  OCTET STRING
                  ACCESS  read-only
                  STATUS  mandatory
                  DESCRIPTION
                  "The Field Replaceable Unit (FRU) number of this component."
                  ::= { componentInventoryEntry 8 }

      componentInventoryFRUSerialNumber  OBJECT-TYPE
                  SYNTAX  OCTET STRING
                  ACCESS  read-only
                  STATUS  mandatory
                  DESCRIPTION
                  "The Field Replaceable Unit (FRU) serial number of this component."
                  ::= { componentInventoryEntry 9 }

      componentInventoryManufacture  OBJECT-TYPE
                  SYNTAX  OCTET STRING
                  ACCESS  read-only
                  STATUS  mandatory
                  DESCRIPTION
                  "The text description of the manufacturer of this component."
                  ::= { componentInventoryEntry 10 }

      componentInventoryHardwareRevision  OBJECT-TYPE
                  SYNTAX  OCTET STRING
                  ACCESS  read-only
                  STATUS  mandatory
                  DESCRIPTION
                  "The hardware revision number of the this component."
                  ::= { componentInventoryEntry 11 }

      componentInventoryManufactureDate  OBJECT-TYPE
                  SYNTAX  OCTET STRING
                  ACCESS  read-only
                  STATUS  mandatory
                  DESCRIPTION
                  "The date when the manufacturer created this component. The format
                   is XXYY, where XX is the week number of the year 20YY."
                  ::= { componentInventoryEntry 12 }

      componentInventoryUUID  OBJECT-TYPE
                  SYNTAX  OCTET STRING
                  ACCESS  read-only
                  STATUS  mandatory
                  DESCRIPTION
                  "The Universally Unique IDentifier (UUID) of this component, represented
                   as a 16 byte hex number."
                  ::= { componentInventoryEntry 13 }

      componentInventoryProductID  OBJECT-TYPE
                  SYNTAX  OCTET STRING
                  ACCESS  read-only
                  STATUS  mandatory
                  DESCRIPTION
                  "The product identifier of the component assigned by the
                   manufacturer."
                  ::= { componentInventoryEntry 14 }

      componentInventorySubManufactureID  OBJECT-TYPE
                  SYNTAX  OCTET STRING
                  ACCESS  read-only
                  STATUS  mandatory
                  DESCRIPTION
                  "The text sub-description of the manufacturer of this component, often
                   used to identify a supplier for a component which has multiple
                   suppliers."
                  ::= { componentInventoryEntry 15 }

      componentInventoryCLEI  OBJECT-TYPE
                  SYNTAX  OCTET STRING
                  ACCESS  read-only
                  STATUS  mandatory
                  DESCRIPTION
                  "The Common Language Equipment Identifier (CLEI) of this component."
                  ::= { componentInventoryEntry 16 }

      componentInventoryAssetTag  OBJECT-TYPE
                  SYNTAX  OCTET STRING
                  ACCESS  read-only
                  STATUS  mandatory
                  DESCRIPTION
                  "The asset tag of this component."
                  ::= { componentInventoryEntry 17 }

      componentInventorySpeed  OBJECT-TYPE
                  SYNTAX  OCTET STRING
                  ACCESS  read-only
                  STATUS  mandatory
                  DESCRIPTION
                  "A speed designation for the component, for example, processor
                   speed."
                  ::= { componentInventoryEntry 18 }

      componentInventoryIdentifier  OBJECT-TYPE
                  SYNTAX  OCTET STRING
                  ACCESS  read-only
                  STATUS  mandatory
                  DESCRIPTION
                  "A unique identifier assigned by the manufacturer to the
                   component, for example,
                   a processor ID."
                  ::= { componentInventoryEntry 19 }

      componentInventorySize  OBJECT-TYPE
                  SYNTAX  INTEGER
                  ACCESS  read-only
                  STATUS  mandatory
                  DESCRIPTION
                  "A size designation for  the component, for example, a memory
                   DIMM size
                   or hard drive capacity."
                  ::= { componentInventoryEntry 20 }

      componentInventoryMemoryType  OBJECT-TYPE
                  SYNTAX  INTEGER  {
                        fpmdram(1),
                        edo(2),
                        edodram(3),
                        sdram(4),
                        multiplexedram(5),
                        ddrsgram(6),
                        ddrsdram(7),
                        ddr2sdrm(8),
                        ddr3sdram(11)
                  }
                  ACCESS  read-only
                  STATUS  mandatory
                  DESCRIPTION
                  "The architecture specification of a memory device."
                  ::= { componentInventoryEntry 21 }

      componentInventoryProductName  OBJECT-TYPE
                  SYNTAX  OCTET STRING
                  ACCESS  read-only
                  STATUS  mandatory
                  DESCRIPTION
                  "The product name assigned by the manufacturer for this component.

                   For more detail, also refer to the componentInventoryDescription
                   object."
                  ::= { componentInventoryEntry 22 }

      componentInventoryProductVersion  OBJECT-TYPE
                  SYNTAX  OCTET STRING
                  ACCESS  read-only
                  STATUS  mandatory
                  DESCRIPTION
                  "The product version  assigned by the manufacturer for this
                   component."
                  ::= { componentInventoryEntry 23 }

      componentInventoryProcessorType  OBJECT-TYPE
                  SYNTAX  INTEGER  {
                        other(1),
                        unknown(2),
                        central(3),
                        math(4),
                        dsp(5),
                        video(6)
                  }
                  ACCESS  read-only
                  STATUS  mandatory
                  DESCRIPTION
                  "The type designation for processor components."
                  ::= { componentInventoryEntry 24 }

      componentInventoryProcessorFamily  OBJECT-TYPE
                  SYNTAX  OCTET STRING
                  ACCESS  read-only
                  STATUS  mandatory
                  DESCRIPTION
                  "The family designation for processor components."
                  ::= { componentInventoryEntry 25 }

      componentInventoryProcessorCores  OBJECT-TYPE
                  SYNTAX  OCTET STRING
                  ACCESS  read-only
                  STATUS  mandatory
                  DESCRIPTION
                  "The number of cores present on a processor component."
                  ::= { componentInventoryEntry 26 }

      componentInventoryProcessorThreads  OBJECT-TYPE
                  SYNTAX  OCTET STRING
                  ACCESS  read-only
                  STATUS  mandatory
                  DESCRIPTION
                  "The number of threads present on a processor component."
                  ::= { componentInventoryEntry 27 }

      componentInventoryProcessorL1DCache  OBJECT-TYPE
                  SYNTAX  OCTET STRING
                  ACCESS  read-only
                  STATUS  mandatory
                  DESCRIPTION
                  "The level 1 data cache size of a processor component."
                  ::= { componentInventoryEntry 28 }

      componentInventoryProcessorL1ICache  OBJECT-TYPE
                  SYNTAX  OCTET STRING
                  ACCESS  read-only
                  STATUS  mandatory
                  DESCRIPTION
                  "The level 1 instruction cache size of a processor component."
                  ::= { componentInventoryEntry 29 }

      componentInventoryProcessorL2Cache  OBJECT-TYPE
                  SYNTAX  OCTET STRING
                  ACCESS  read-only
                  STATUS  mandatory
                  DESCRIPTION
                  "The level 2 cache size of a processor component."
                  ::= { componentInventoryEntry 30 }

      componentInventoryProcessorL3Cache  OBJECT-TYPE
                  SYNTAX  OCTET STRING
                  ACCESS  read-only
                  STATUS  mandatory
                  DESCRIPTION
                  "The level 3 cache size of a processor component."
                  ::= { componentInventoryEntry 31 }

      componentInventoryProcessorVoltage  OBJECT-TYPE
                  SYNTAX  OCTET STRING
                  ACCESS  read-only
                  STATUS  mandatory
                  DESCRIPTION
                  "The voltage rating for a processor component."
                  ::= { componentInventoryEntry 32 }

      componentInventoryProcessorExtClock  OBJECT-TYPE
                  SYNTAX  OCTET STRING
                  ACCESS  read-only
                  STATUS  mandatory
                  DESCRIPTION
                  "The external clock speed of a processor component."
                  ::= { componentInventoryEntry 33 }

      componentInventoryProcessorDataWidth  OBJECT-TYPE
                  SYNTAX  OCTET STRING
                  ACCESS  read-only
                  STATUS  mandatory
                  DESCRIPTION
                  "The maximum data bus width capability of a processor component,
                   expressed typically in bits."
                  ::= { componentInventoryEntry 34 }

      componentInventoryManufactureIDNum  OBJECT-TYPE
                  SYNTAX  INTEGER
                  ACCESS  read-only
                  STATUS  mandatory
                  DESCRIPTION
                  "The identification number assigned for the component by the manufacturer."
                  ::= { componentInventoryEntry 35 }

      componentInventoryGlobalID  OBJECT-TYPE
                  SYNTAX  OCTET STRING
                  ACCESS  read-only
                  STATUS  mandatory
                  DESCRIPTION
                  "The global identifier (GLID) of this component.  This ID is a
                   unique identifier for the CMM chassis (midplane), set by the
                   manufacturer.
                   This ID and the associated inventory is passed back to support
                   via the Electronic Service Agent and the Call Home feature.
                   This ID and the accompanying chassis inventory will be
                   stored and retained resulting in a
                   configuration/change history file of the inventory for a
                   chassis associated with a particular GLID.
                   This ID can be used by a customer to identify and categorize
                   all the content that resides within a chassis, much like a
                   physical serial number is associated with a single box
                   server."
                  ::= { componentInventoryEntry 41 }

      -- *************************************************************************
     -- componentInventoryTableCacheTimeout
     -- *************************************************************************
     componentInventoryTableCacheTimeout OBJECT-TYPE
                   SYNTAX  INTEGER
                   ACCESS  read-only
                   STATUS  mandatory
                   DESCRIPTION
                   "The timeout value (in seconds) of the cached data for the
                   table, componentInventoryTable.
                   This value is static (constant) and cannot be set."
                   ::= { componentInventory 2 }

      -- *************************************************************************
      -- Component Firmware Information
      -- *************************************************************************
      componentFirmware OBJECT IDENTIFIER ::= { componentInformation 2 }

      componentFirmwareTable OBJECT-TYPE
                    SYNTAX  SEQUENCE OF ComponentFirmwareEntry
                    ACCESS  not-accessible
                    STATUS  mandatory
                    DESCRIPTION
                    "Table of component firmware information. Not all components will
                     provide every object defined in the ComponentFirmwareEntry."
                    ::= { componentFirmware 1 }

      componentFirmwareEntry OBJECT-TYPE
                    SYNTAX ComponentFirmwareEntry
                    ACCESS  not-accessible
                    STATUS  mandatory
                    DESCRIPTION
                    "Component firmware information."
                    INDEX { componentFirmwareTopologyPath, componentFirmwareIndex }
                    ::= { componentFirmwareTable 1 }

      ComponentFirmwareEntry ::= SEQUENCE {
                  componentFirmwareTopologyPath OCTET STRING,
                  componentFirmwareIndex INTEGER,
                  componentFirmwareComponentInstance INTEGER,
                  componentFirmwareComponentDescription OCTET STRING,
                  componentFirmwareType OCTET STRING,
                  componentFirmwareBuildID OCTET STRING,
                  componentFirmwareReleaseDate OCTET STRING,
                  componentFirmwareFilename OCTET STRING,
                  componentFirmwareRevision OCTET STRING,
                  componentFirmwareRevisionMajor INTEGER,
                  componentFirmwareRevisionMinor INTEGER,
                  componentFirmwareLevelStatus OCTET STRING,
                  componentFirmwarePendingBuildID OCTET STRING,
                  componentFirmwarePendingReleaseDate OCTET STRING,
                  componentFirmwarePendingRevision OCTET STRING,
                  componentFirmwareReleaseLevel OCTET STRING,
                  componentFirmwareImageStatus INTEGER,
		  componentFirmwareRole OCTET STRING,
                  componentFirmwareTypeID INTEGER
                  }

      componentFirmwareTopologyPath  OBJECT-TYPE
                  SYNTAX  OCTET STRING  (SIZE (0..100))
                  ACCESS  read-only
                  STATUS  mandatory
                  DESCRIPTION
                  "The unique identifier for a component in this table. The chassis and each
                   installed component is represented by a hardware topology tree, where
                   each node in the tree represents a component. The path to a particular
                   component consists of one or more <component>,<instance> pairs, where
                   each successive pair is a child of the previous parent pair.

                   As an example, the root of the tree is the chassis and is represented
                   by the pair 'CHASSIS, 1'. This pair indicates the first instance of
                   the chassis. If a blade is inserted in slot 4 of the chassis, its
                   topology path is 'CHASSIS, 1, BLADE, 4'. With this format, the
                   components in the chassis can be determined along with their relative
                   hierarchy to each other.

                   Note that this TP is preceded by a single octet that specifies the TP length.
                   This is required since this table is indexed with two indices and, therefore,
                   the TP length must be explicitly provided.

                   This component firmware table is indexed by this unique topology
                   path and the numeric designations for the components are:

                    CHASSIS,                0x01   Chassis
                    MM,                     0x02   Management Module
                    BLADE,                  0x03   Main system board of a blade
                    POWER,                  0x04   Power Supply, Power Module, etc
                    COOLING,                0x05   Fan, blower, or other cooling device
                    IO_MODULE,              0x06   Has I/O interface, i.e. - switch or bridge
                    MEDIA,                  0x07   Media device
                    PROCESSOR,              0x08   Any processor, processor module, etc
                    STORAGE,                0x09   Any type of storage device
                    EXPANSION,              0x0A   Expansion Card (not covered by more specific type)
                    MEMORY,                 0x0B   Any memory device, module, etc
                    MFRU,                   0x0C   Managed FRU Device
                    PANEL,                  0x0D   Any sort of panel device, such as a front panel
                    BLADE_EXPANSION_MODULE, 0x0E   Expansion option (BEM) such as PEU, BSE, etc
                    CARD_EXPANSION,         0x0F   Expansion card, ie. daughter card
                    CARD_HS_EXPANSION,      0x10   High Speed Expansion card, ie. daughter card
                    INTERPOSER,             0x11   Interposer device
                    CLOCK,                  0x12   Clock card
                    MUX,                    0x13   Mulitplexer card
                    ADDIN,                  0x14   cKVM card & other addin cards
                    STORAGE_MODULE,         0x15   Container of one or more Storage Devices
                    SYS_EXPANSION_CARD,     0x16   Management card
                    BATTERY,                0x17   A single battery
                    BATTERY_MODULE,         0x18   Container of one or more batteries
                    REAR_LED,               0x19   Rear LED card
                    MEMORY_BANK,            0x1A   Memory banks
                    AIR_FILTER,             0x1B   Filter mechanism (bezel)
                    SERIAL_PORT_MODULE,     0x1C   Container of one or more serial ports
                    PARENT,                 0x1D   Reference to parent for multi-parent support
                    PHY_PORT,               0x1E   Physical port
                    IO_EXPANDER,            0x1F   RAID card
                    CABLE,                  0x20   Cable/Interconnect
                    FAN_MUX,                0x29   Fan multiplexer card
                     PCI_EXPRESS,            0x32   PCI express card on (PEN)
                     FLASH_DIMM,             0x33   Used for SPD devices that matches the silkscreen of the DIMM slot
                     RACK,                   0x50   Rack
                     PLATFORM,               0x51   Generic Platform like rack mounted server/appliance
                     DATAPLEX,               0x52   DataPlex
                     OTHER,                  0x53   Other unknown etc.
                     PERIPHERAL_MODULE,      0x54 
                     SYSTEM_BOARD,           0x55   System board
                     PROCESSOR_MODULE,       0x56 
                     BACK_PANEL,             0x57 
                     POWER_SYSTEM_BOARD,     0x58 
                     STORAGE_BACKPLANE,      0x59   Drive back plane
                     PROC_BOARD,             0x5A   Holds 1 or more processors
                     POWER_DI,               0x5B   Power mgt / power distribution board
                     CHASSIS_BACK_PANEL,     0x5C 
                     SUB_CHASSIS,            0x5D 
                     OTHER_CHASSIS_BOARD,    0x5E 
                     DEVICE_MODULE,          0x5F 
                     REMOTE_DEVICE,          0x60   Remote mgt communication device
                     EXTERNAL_ENVIRONMENT,   0x61   Such as external temp sensor for outside box temps
                     PROC_MEMORY_MODULE,     0x62   Processors and memory on same module"

                  ::= { componentFirmwareEntry 1 }

      componentFirmwareIndex  OBJECT-TYPE
                  SYNTAX  INTEGER
                  ACCESS  read-only
                  STATUS  mandatory
                  DESCRIPTION
                  "Each component may have one or more types of firmware associated with it, and this index object
                   identifies the particular instance."
                  ::= { componentFirmwareEntry 2 }

      componentFirmwareComponentInstance  OBJECT-TYPE
                  SYNTAX  INTEGER
                  ACCESS  read-only
                  STATUS  mandatory
                  DESCRIPTION
                  "The slot number or instance of a particular component. Typically,
                   if the component plugs into the chassis, this represents the slot
                   number. However, some components are connected to another component,
                   and this represents the instance. For example, a blade may have
                   several expansion cards that connect to the blade system planar,
                   and in this case, this value identifies which expansion card
                   instance the row represents.

                   Note that this slot/instance value can be determined from the
                   componentFirmwareTopologyPath object, but this
                   componentFirmwareComponentInstance object is provided as a convenience
                   to the user."
                  ::= { componentFirmwareEntry 3 }

      componentFirmwareComponentDescription  OBJECT-TYPE
                  SYNTAX  OCTET STRING
                  ACCESS  read-only
                  STATUS  mandatory
                  DESCRIPTION
                  "A short text string describing the particular component. For the
                   MM and blades, this name will be the configured name or its
                   serial number if no user configured name is available. For all
                   other components, this object will provide text to identify the
                   component. If a text string is not available, a value of
                   'Not available' is presented.

                   For more detail, also refer to the componentInventoryProductName
                   object."
                  ::= { componentFirmwareEntry 4 }

      componentFirmwareType  OBJECT-TYPE
                  SYNTAX  OCTET STRING
                  ACCESS  read-only
                  STATUS  mandatory
                  DESCRIPTION
                  "A text description of the type of firmware load."
                  ::= { componentFirmwareEntry 5 }

      componentFirmwareBuildID  OBJECT-TYPE
                  SYNTAX  OCTET STRING
                  ACCESS  read-only
                  STATUS  mandatory
                  DESCRIPTION
                  "A text description of the build identifier for this firmware load."
                  ::= { componentFirmwareEntry 6 }

      componentFirmwareReleaseDate  OBJECT-TYPE
                  SYNTAX  OCTET STRING
                  ACCESS  read-only
                  STATUS  mandatory
                  DESCRIPTION
                  "A text description of the release date for this firmware load."
                  ::= { componentFirmwareEntry 7 }

      componentFirmwareFilename  OBJECT-TYPE
                  SYNTAX  OCTET STRING
                  ACCESS  read-only
                  STATUS  mandatory
                  DESCRIPTION
                  "A text description of the filename of this firmware load."
                  ::= { componentFirmwareEntry 8 }

      componentFirmwareRevision  OBJECT-TYPE
                  SYNTAX  OCTET STRING
                  ACCESS  read-only
                  STATUS  mandatory
                  DESCRIPTION
                  "A text description of the revision level of this firmware load."
                  ::= { componentFirmwareEntry 9 }

      componentFirmwareRevisionMajor  OBJECT-TYPE
                  SYNTAX  INTEGER
                  ACCESS  read-only
                  STATUS  mandatory
                  DESCRIPTION
                  "A numeric identifier of the revision major number for this firmware load."
                  ::= { componentFirmwareEntry 10 }

      componentFirmwareRevisionMinor  OBJECT-TYPE
                  SYNTAX  INTEGER
                  ACCESS  read-only
                  STATUS  mandatory
                  DESCRIPTION
                  "A numeric identifier of the revision minor number for this firmware load."
                  ::= { componentFirmwareEntry 11 }

      componentFirmwareLevelStatus OBJECT-TYPE
                    SYNTAX  OCTET STRING
                    ACCESS  read-only
                    STATUS  mandatory
                    DESCRIPTION
                    "The level status of the firmware build ID.
                    It has three possible values as Different (mismatch firmware build ID), Match (the
                    same firmware build ID), Unique (only one such firmware build ID)."
                  ::= { componentFirmwareEntry 12 }
                  
       componentFirmwarePendingBuildID  OBJECT-TYPE
                  SYNTAX  OCTET STRING
                  ACCESS  read-only
                  STATUS  mandatory
                  DESCRIPTION
                  "A text description of the build identifier for this pending firmware load."
                  ::= { componentFirmwareEntry 13 }

      componentFirmwarePendingReleaseDate  OBJECT-TYPE
                  SYNTAX  OCTET STRING
                  ACCESS  read-only
                  STATUS  mandatory
                  DESCRIPTION
                  "A text description of the release date for this pending firmware load."
                  ::= { componentFirmwareEntry 14 }

      componentFirmwarePendingRevision  OBJECT-TYPE
                  SYNTAX  OCTET STRING
                  ACCESS  read-only
                  STATUS  mandatory
                  DESCRIPTION
                  "A text description of the revision level of this pending firmware load."
                  ::= { componentFirmwareEntry 15 }

      componentFirmwareReleaseLevel  OBJECT-TYPE
                  SYNTAX  OCTET STRING
                  ACCESS  read-only
                  STATUS  mandatory
                  DESCRIPTION
                  "A text description of the firmware release level this firmware load."
                  ::= { componentFirmwareEntry 16 }

      componentFirmwareImageStatus  OBJECT-TYPE
                  SYNTAX  INTEGER {
                     inactive(0),
                     active(1),
		     na(255)
                  }
                  ACCESS  read-only
                  STATUS  mandatory
                  DESCRIPTION
                  "This object indicates whether this firmware image is the
                  active (1) firmware,otherwise this firmware image is inactive (0)."
                  ::= { componentFirmwareEntry 17 }

      componentFirmwareRole  OBJECT-TYPE
		  SYNTAX OCTET STRING
		  ACCESS read-only
		  STATUS mandatory
		  DESCRIPTION
		  "A text description with the firmware image information."
		  ::= { componentFirmwareEntry 18 }

      componentFirmwareTypeID  OBJECT-TYPE
                  SYNTAX  INTEGER {
                    bladeFwBios(1),
                    bladeDiagnostics(2),
                    bladeSysMgmtProcessor(3),
                    bladeFpga(4),
                    bladecKVM(5),
		    bladeMP(6),
		    bladeUEFI(7),
		    bladeDSA(8),
		    switchModuleMainAppl(40),
                    switchModuleMainAppl1(41),
                    switchModuleMainAppl2(42),
                    switchModuleBootROM(43),
                    mgmtModuleMainAppl(61),
                    mgmtModuleMainApplPendingRestart(62),
                    fanController(81),
                    powerSupplyFirmware(91),
                    powerSupplyFanController(92),
		    expansionCardGeneric(101),
		    expansionCardEfi(102),
		    expansionCardFcode(103),
		    expansionCardBios(104),
		    expansionCardMain(105),
		    expansionCardMulti(106),
                    unknown(255)
                  }
                  ACCESS  read-only
                  STATUS  mandatory
                  DESCRIPTION
                  "Indicates the type of firmware load with a numeric identifier."
                  ::= { componentFirmwareEntry 20 }


      -- *************************************************************************
      -- componentFirmwareTableCacheTimeout
      -- *************************************************************************
      componentFirmwareTableCacheTimeout OBJECT-TYPE
                   SYNTAX  INTEGER
                   ACCESS  read-only
                   STATUS  mandatory
                   DESCRIPTION
                   "The timeout value (in seconds) of the cached data for the
                   table, componentFirmwareTable.
                   This value is static (constant) and cannot be set."
                   ::= { componentFirmware 2 }


      componentInventoryReady OBJECT-TYPE
                   SYNTAX  INTEGER {
                     notReady(0),
                     ready(1)
                   }
                   ACCESS  read-only
                   STATUS  mandatory
                   DESCRIPTION
                   "When a blade management controller, switch or the MM is reset, the 
                    inventory data is refreshed in the MM database. This includes
                    items like VPD (e.g. - serial number, UUID) and MAC address information.
                    
                    Applications need to know when this information has been populated on the MM
                    before they begin to query it using SNMP or other means. This simple flag 
                    object will return a ready or notReady indication when all blades and switches 
                    have completed initialization and the inventory information has been provided 
                    to the MM. 
                    
                    Note that due to components that may be experiencing a 'communication failure' or 
                    'initialization failure' condition, this object may continue to show notReady.   
                    Therefore, any application that polls this object should also incorporate a timeout 
                    
                    A more granular, per-blade status is available via the bladeSystemStatusTable"
                   ::= { componentInformation 3 }

      nodeFirmwareAnalysisTable OBJECT-TYPE
                    SYNTAX SEQUENCE OF NodeFirmwareAnalysisEntry
                    ACCESS not-accessible
                    STATUS mandatory
                    DESCRIPTION
                    "Table of firmware levels of installed nodes. This information is grouped by
                     Machine Type/Model and includes two or more nodes with the same Type/Model.
                     This information is intended to be used in determining which components
                     firmware may need upgrade."
                     ::= { componentFirmware 7 }

      nodeFirmwareAnalysisEntry OBJECT-TYPE
                     SYNTAX NodeFirmwareAnalysisEntry
                     ACCESS not-accessible
                     STATUS mandatory
                     DESCRIPTION
                     "Node firmware analysis information."
                     INDEX { nodeFirmwareAnalysisIndex }
                     ::= { nodeFirmwareAnalysisTable 1 }

       NodeFirmwareAnalysisEntry ::= SEQUENCE {
                     nodeFirmwareAnalysisIndex INTEGER,
                     nodeFirmwareAnalysisMachineTypeModel OCTET STRING,
                     nodeFirmwareAnalysisFirmwareType OCTET STRING,
                     nodeFirmwareAnalysisBuildId OCTET STRING,
                     nodeFirmwareAnalysisReleaseDate OCTET STRING,
                     nodeFirmwareAnalysisRevisionLevel OCTET STRING,
                     nodeFirmwareAnalysisTopology OCTET STRING,
                     nodeFirmwareAnalysisDeviceName OCTET STRING
                     }

        nodeFirmwareAnalysisIndex OBJECT-TYPE
                     SYNTAX INTEGER
                     ACCESS read-only
                     STATUS mandatory
                     DESCRIPTION
                     "The index for the node firmware levels."
                     ::={ nodeFirmwareAnalysisEntry 1 }

         nodeFirmwareAnalysisMachineTypeModel OBJECT-TYPE
                     SYNTAX OCTET STRING
                     ACCESS read-only
                     STATUS mandatory
                     DESCRIPTION
                     "The machine type or model of node firmware."
                     ::={ nodeFirmwareAnalysisEntry 2 }

         nodeFirmwareAnalysisFirmwareType OBJECT-TYPE
                     SYNTAX OCTET STRING
                     ACCESS read-only
                     STATUS mandatory
                     DESCRIPTION
                     "The firmware type."
                     ::={ nodeFirmwareAnalysisEntry 3 }

         nodeFirmwareAnalysisBuildId OBJECT-TYPE
                     SYNTAX OCTET STRING
                     ACCESS read-only
                     STATUS mandatory
                     DESCRIPTION
                     "The firmware build id."
                     ::={ nodeFirmwareAnalysisEntry 4 }

	 nodeFirmwareAnalysisReleaseDate OBJECT-TYPE
                     SYNTAX OCTET STRING
                     ACCESS read-only
                     STATUS mandatory
                     DESCRIPTION
                     "The firmware release date."
                     ::={ nodeFirmwareAnalysisEntry 5 }


          nodeFirmwareAnalysisRevisionLevel  OBJECT-TYPE
                     SYNTAX OCTET STRING
                     ACCESS read-only
                     STATUS mandatory
                     DESCRIPTION
                     "The firmware revision level."
                     ::={ nodeFirmwareAnalysisEntry 6 }

          nodeFirmwareAnalysisTopology   OBJECT-TYPE
                     SYNTAX OCTET STRING
                     ACCESS read-only
                     STATUS mandatory
                     DESCRIPTION
                     "The node topology."
                     ::={ nodeFirmwareAnalysisEntry 7 }

          nodeFirmwareAnalysisDeviceName   OBJECT-TYPE
                     SYNTAX OCTET STRING
                     ACCESS read-only
                     STATUS mandatory
                     DESCRIPTION
                     "The node device name."
                     ::={ nodeFirmwareAnalysisEntry 8 }

      smFirmwareAnalysisTable OBJECT-TYPE
		SYNTAX SEQUENCE OF SmFirmwareAnalysisEntry
		ACCESS not-accessible
		STATUS mandatory
                DESCRIPTION
		"Table of firmware levels of installed IOMs. This information is grouped by Product Id
		 and includes two or more IOMs with the same product id.
		 This information is intended to be used in determining which components firmware
		 may need upgrade."
		::= { componentFirmware 11 }

      smFirmwareAnalysisEntry OBJECT-TYPE
	        SYNTAX SmFirmwareAnalysisEntry
		ACCESS not-accessible
		STATUS mandatory
		DESCRIPTION
		"IOM firmware analysis information."
		INDEX { smFirmwareAnalysisIndex }
		::= { smFirmwareAnalysisTable 1 }

     SmFirmwareAnalysisEntry ::= SEQUENCE {
		smFirmwareAnalysisIndex INTEGER,
		smFirmwareAnalysisProductId OCTET STRING,
		smFirmwareAnalysisProductName OCTET STRING,
		smFirmwareAnalysisFirmwareType OCTET STRING,
		smFirmwareAnalysisFirmwareVersion OCTET STRING,
		smFirmwareAnalysisReleaseDate OCTET STRING,
		smFirmwareAnalysisTopology OCTET STRING
		}

     smFirmwareAnalysisIndex OBJECT-TYPE
		SYNTAX INTEGER
		ACCESS read-only
		STATUS mandatory
		DESCRIPTION
		"The index for the IOM firmware levels."
		::={ smFirmwareAnalysisEntry 1 }

     smFirmwareAnalysisProductId OBJECT-TYPE
	       SYNTAX OCTET STRING
	       ACCESS read-only
	       STATUS mandatory
	       DESCRIPTION
	       "The IOM product id."
	       ::={ smFirmwareAnalysisEntry 2 }


     smFirmwareAnalysisProductName OBJECT-TYPE
               SYNTAX OCTET STRING
               ACCESS read-only
               STATUS mandatory
               DESCRIPTION
               "The IOM product name."
               ::={ smFirmwareAnalysisEntry 3 }

      smFirmwareAnalysisFirmwareType OBJECT-TYPE
               SYNTAX OCTET STRING
               ACCESS read-only
               STATUS mandatory
               DESCRIPTION
               "The IOM firmware type."
               ::={ smFirmwareAnalysisEntry 4 }

       smFirmwareAnalysisFirmwareVersion OBJECT-TYPE
               SYNTAX OCTET STRING
               ACCESS read-only
               STATUS mandatory
               DESCRIPTION
               "The IOM firmware version."
               ::={ smFirmwareAnalysisEntry 5 }

       smFirmwareAnalysisReleaseDate OBJECT-TYPE
               SYNTAX OCTET STRING
               ACCESS read-only
               STATUS mandatory
               DESCRIPTION
               "The IOM release date."
               ::={ smFirmwareAnalysisEntry 6 }

       smFirmwareAnalysisTopology OBJECT-TYPE
               SYNTAX OCTET STRING
               ACCESS read-only
               STATUS mandatory
               DESCRIPTION
               "The IOM topology."
               ::={ smFirmwareAnalysisEntry 7 }

      componentDriveTable OBJECT-TYPE
                    SYNTAX  SEQUENCE OF ComponentDriveEntry
                    ACCESS  not-accessible
                    STATUS  mandatory
                    DESCRIPTION
                    "Table of information indicating presence of a disk drive on a component.
                     The management module does not receive any inventory VPD from the
                     component, so only the presence of a drive can be indicated by this table."
                    ::= { componentInformation 10 }

      componentDriveEntry OBJECT-TYPE
                    SYNTAX ComponentDriveEntry
                    ACCESS  not-accessible
                    STATUS  mandatory
                    DESCRIPTION
                    "Component drive information."
                    INDEX { componentDriveTopologyPath }
                    ::= { componentDriveTable 1 }

      ComponentDriveEntry ::= SEQUENCE {
                  componentDriveTopologyPath OCTET STRING,
                  componentDriveDescription OCTET STRING
                  }

      componentDriveTopologyPath  OBJECT-TYPE
                  SYNTAX  OCTET STRING  (SIZE (0..100))
                  ACCESS  read-only
                  STATUS  mandatory
                  DESCRIPTION
                  "The unique identifier for a row in this table. The chassis and each
                   installed component is represented by a hardware topology tree, where
                   each node in the tree represents a component. The path to a particular
                   component consists of one or more <component>,<instance> pairs, where
                   each successive pair is a child of the previous parent pair.

                   As an example, the root of the tree is the chassis and is represented
                   by the pair 'CHASSIS, 1'. This pair indicates the first instance of
                   the chassis. If a blade is inserted in slot 4 of the chassis, its
                   topology path is 'CHASSIS, 1, BLADE, 4'. With this format, the
                   components in the chassis can be determined along with their relative
                   hierarchy to each other.

                   This component table is indexed by this unique topology
                   path and the numeric designations for the components are:

                    CHASSIS,                0x01   Chassis
                    MM,                     0x02   Management Module
                    BLADE,                  0x03   Main system board of a blade
                    POWER,                  0x04   Power Supply, Power Module, etc
                    COOLING,                0x05   Fan, blower, or other cooling device
                    IO_MODULE,              0x06   Has I/O interface, i.e. - switch or bridge
                    MEDIA,                  0x07   Media device
                    PROCESSOR,              0x08   Any processor, processor module, etc
                    STORAGE,                0x09   Any type of storage device
                    EXPANSION,              0x0A   Expansion Card (not covered by more specific type)
                    MEMORY,                 0x0B   Any memory device, module, etc
                    MFRU,                   0x0C   Managed FRU Device
                    PANEL,                  0x0D   Any sort of panel device, such as a front panel
                    BLADE_EXPANSION_MODULE, 0x0E   Expansion option (BEM) such as PEU, BSE, etc
                    CARD_EXPANSION,         0x0F   Expansion card, ie. daughter card
                    CARD_HS_EXPANSION,      0x10   High Speed Expansion card, ie. daughter card
                    INTERPOSER,             0x11   Interposer device
                    CLOCK,                  0x12   Clock card
                    MUX,                    0x13   Mulitplexer card
                    ADDIN,                  0x14   cKVM card & other addin cards
                    STORAGE_MODULE,         0x15   Container of one or more Storage Devices
                    SYS_EXPANSION_CARD,     0x16   Management card
                    BATTERY,                0x17   A single battery
                    BATTERY_MODULE,         0x18   Container of one or more batteries
                    MEDIA_MODULE,           0x19   Container of one or more media devices
                    MEMORY_BANK,            0x1A   Memory banks
                    AIR_FILTER,             0x1B   Filter mechanism (bezel)
                    SERIAL_PORT_MODULE,     0x1C   Container of one or more serial ports
                    PARENT,                 0x1D   Reference to parent for multi-parent support
                    PHY_PORT,               0x1E   Physical port
                    IO_EXPANDER,            0x1F   RAID card"
                  ::= { componentDriveEntry 1 }

      componentDriveDescription  OBJECT-TYPE
                  SYNTAX  OCTET STRING
                  ACCESS  read-only
                  STATUS  mandatory
                  DESCRIPTION
                  "A short text string describing the particular drive on the component."
                  ::= { componentDriveEntry 2 }

      -- *************************************************************************
      -- componentDriveTableCacheTimeout
      -- *************************************************************************
      componentDriveTableCacheTimeout OBJECT-TYPE
                   SYNTAX  INTEGER
                   ACCESS  read-only
                   STATUS  mandatory
                   DESCRIPTION
                   "The timeout value (in seconds) of the cached data for the
                   table, componentDriveTable.
                   This value is static (constant) and cannot be set."
                   ::= { componentInformation 11 }

      -- *************************************************************************
      -- License Key Information
      --
      -- This anchor is for tables that provide information about the
      -- License Keys for components in the chassis.
      --
      -- *************************************************************************

      licenseKeyInfo  OBJECT IDENTIFIER ::= { monitors 30 }

      licenseKeyInfoTable OBJECT-TYPE
                    SYNTAX  SEQUENCE OF LicenseKeyInfoEntry
                    ACCESS  not-accessible
                    STATUS  mandatory
                    DESCRIPTION
                    "Table of license key information."
                    ::= { licenseKeyInfo 1 }

     licenseKeyInfoEntry OBJECT-TYPE
                    SYNTAX LicenseKeyInfoEntry
                    ACCESS  not-accessible
                    STATUS  mandatory
                    DESCRIPTION
                    "License key information entry."
                    INDEX { licenseKeyComponentIndex, licenseKeyIndex }
                    ::= { licenseKeyInfoTable 1 }

     LicenseKeyInfoEntry ::= SEQUENCE {
                    licenseKeyComponentIndex INTEGER,
                    licenseKeyIndex INTEGER,
                    licenseKeyDescription OCTET STRING,
                    licenseKeyTimestamp OCTET STRING,
                    licenseKeyLicenseID OCTET STRING,
                    licenseKeyOtherInfo OCTET STRING,
                    licenseKeyStatus INTEGER
                    }

     licenseKeyComponentIndex OBJECT-TYPE
                   SYNTAX  INTEGER {
                     blade1(1),
                     blade2(2),
                     blade3(3),
                     blade4(4),
                     blade5(5),
                     blade6(6),
                     blade7(7),
                     blade8(8),
                     blade9(9),
                     blade10(10),
                     blade11(11),
                     blade12(12),
                     blade13(13),
                     blade14(14),
                     switchModule1(41),
                     switchModule2(42),
                     switchModule3(43),
                     switchModule4(44)
                   }
                   ACCESS  read-only
                   STATUS  mandatory
                   DESCRIPTION
                   "License key component table index."
                   ::= { licenseKeyInfoEntry 1 }

     licenseKeyIndex    OBJECT-TYPE
                   SYNTAX  INTEGER (1..255)
                   ACCESS  read-only
                   STATUS  mandatory
                   DESCRIPTION
                   "The license key index for the chassis component."
                   ::= { licenseKeyInfoEntry 2 }

     licenseKeyDescription   OBJECT-TYPE
                   SYNTAX   OCTET STRING
                   ACCESS  read-only
                   STATUS  mandatory
                   DESCRIPTION
                   "The description for a license key."
                   ::= { licenseKeyInfoEntry 3 }

     licenseKeyTimestamp   OBJECT-TYPE
                   SYNTAX   OCTET STRING
                   ACCESS  read-only
                   STATUS  mandatory
                   DESCRIPTION
                   "The date and time of this license key."
                   ::= { licenseKeyInfoEntry 4 }

     licenseKeyLicenseID   OBJECT-TYPE
                   SYNTAX   OCTET STRING
                   ACCESS  read-only
                   STATUS  mandatory
                   DESCRIPTION
                   "The unique identifier for this license key."
                   ::= { licenseKeyInfoEntry 5 }

     licenseKeyOtherInfo   OBJECT-TYPE
                   SYNTAX   OCTET STRING
                   ACCESS  read-only
                   STATUS  mandatory
                   DESCRIPTION
                   "Any other information related to this license key."
                   ::= { licenseKeyInfoEntry 6 }

     licenseKeyStatus OBJECT-TYPE
                   SYNTAX  INTEGER {
                     unknown(0),
                     valid(1),
                     invalid(2),
                     expired(3),
                     usageExceeded(4),
                     notApplicable(99)
                   }
                   ACCESS  read-only
                   STATUS  mandatory
                   DESCRIPTION
                   "The current status of this license key."
                   ::= { licenseKeyInfoEntry 7 }

      chassisLicenseKeyTable OBJECT-TYPE
                    SYNTAX  SEQUENCE OF ChassisLicenseKeyEntry
                    ACCESS  not-accessible
                    STATUS  mandatory
                    DESCRIPTION
                    "Table of chassis license key information."
                    ::= { licenseKeyInfo 5 }

     chassisLicenseKeyEntry OBJECT-TYPE
                    SYNTAX ChassisLicenseKeyEntry
                    ACCESS  not-accessible
                    STATUS  mandatory
                    DESCRIPTION
                    "Chassis License key information entry."
                    INDEX { chassisLicenseKeyIndex }
                    ::= { chassisLicenseKeyTable 1 }

     ChassisLicenseKeyEntry ::= SEQUENCE {
                    chassisLicenseKeyIndex INTEGER,
                    chassisLicenseKeyFeature OCTET STRING,
                    chassisLicenseKeyFeatureType OCTET STRING,
                    chassisLicenseKeyDescription OCTET STRING,
                    chassisLicenseKeySystem OCTET STRING,
                    chassisLicenseKeyLicenseID OCTET STRING,
                    chassisLicenseKeyValidation OCTET STRING,
                    chassisLicenseKeyStatus INTEGER,
                    chassisLicenseKeyTimeLimit OCTET STRING,
                    chassisLicenseKeyUsageLimit INTEGER
                    }

     chassisLicenseKeyIndex    OBJECT-TYPE
                   SYNTAX  INTEGER (1..255)
                   ACCESS  read-only
                   STATUS  mandatory
                   DESCRIPTION
                   "The key index for the chassis license keys."
                   ::= { chassisLicenseKeyEntry 1 }

     chassisLicenseKeyFeature   OBJECT-TYPE
                   SYNTAX   OCTET STRING
                   ACCESS  read-only
                   STATUS  mandatory
                   DESCRIPTION
                   "The name of the Feature for the license key."
                   ::= { chassisLicenseKeyEntry 2 }

     chassisLicenseKeyFeatureType    OBJECT-TYPE
                   SYNTAX  OCTET STRING
                   ACCESS  read-only
                   STATUS  mandatory
                   DESCRIPTION
                   "The Feature Type Code for the license key."
                   ::= { chassisLicenseKeyEntry 3 }

     chassisLicenseKeyDescription   OBJECT-TYPE
                   SYNTAX   OCTET STRING
                   ACCESS  read-only
                   STATUS  mandatory
                   DESCRIPTION
                   "The description of the license key."
                   ::= { chassisLicenseKeyEntry 4 }

     chassisLicenseKeySystem   OBJECT-TYPE
                   SYNTAX   OCTET STRING
                   ACCESS  read-only
                   STATUS  mandatory
                   DESCRIPTION
                   "System information for the license key."
                   ::= { chassisLicenseKeyEntry 5 }

     chassisLicenseKeyLicenseID   OBJECT-TYPE
                   SYNTAX   OCTET STRING
                   ACCESS  read-only
                   STATUS  mandatory
                   DESCRIPTION
                   "Identification of the license key."
                   ::= { chassisLicenseKeyEntry 6 }

     chassisLicenseKeyValidation   OBJECT-TYPE
                   SYNTAX   OCTET STRING
                   ACCESS  read-only
                   STATUS  mandatory
                   DESCRIPTION
                   "Validation of the license key."
                   ::= { chassisLicenseKeyEntry 7 }

     chassisLicenseKeyStatus OBJECT-TYPE
                   SYNTAX  INTEGER {
                     valid(0),
                     validatingKey(1),
                     invalidMTSN(2),
                     invalidMAC(3),
                     signatureValidationFailed(4),
                     keyExpired(5),
                     usageExceeded(6),
                     validateElsewhere(7),
                     notApplicable(8)
                   }
                   ACCESS  read-only
                   STATUS  mandatory
                   DESCRIPTION
                   "The current status of the license key."
                   ::= { chassisLicenseKeyEntry 8 }

     chassisLicenseKeyTimeLimit   OBJECT-TYPE
                   SYNTAX   OCTET STRING
                   ACCESS  read-only
                   STATUS  mandatory
                   DESCRIPTION
                   "Date and Time (GMT) when license expires."
                   ::= { chassisLicenseKeyEntry 9 }

     chassisLicenseKeyUsageLimit   OBJECT-TYPE
                   SYNTAX   INTEGER
                   ACCESS  read-only
                   STATUS  mandatory
                   DESCRIPTION
                   "Number of times remaining for license usage. A negative value indicates
                    that there is no Usage Limit for the license."
                   ::= { chassisLicenseKeyEntry 10 }

      -- ********************************************************************************
      -- MM Security Settings
      -- ********************************************************************************
      securitySettings        OBJECT IDENTIFIER ::= { configureSP 3 }

      trespassWarning OBJECT-TYPE
                   SYNTAX  INTEGER {
                     disabled(0),
                     enabled(1)
                   }
                   ACCESS  read-write
                   STATUS  mandatory
                   DESCRIPTION
                   "If enabled, a customizable trespass warning message is displayed via the Web
                   and CLI interfaces."
                   ::= { securitySettings 2 }

     trespassWarningDefault OBJECT-TYPE
                   SYNTAX  INTEGER {
                     execute(1)
                   }
                   ACCESS  read-write
                   STATUS  mandatory
                   DESCRIPTION
                   "Reset the trespass warning to default value.
                   NOTE: Value returned for the GET command is meaningless for this MIB object."
                   ::= { securitySettings 3 }

     trespassMessage OBJECT-TYPE
                    SYNTAX  OCTET STRING (SIZE(0..1600))
                    ACCESS  read-write
                    STATUS  mandatory
                    DESCRIPTION
                    "The value of the trespass warning message."
                    ::= { securitySettings  4 }

     -- ********************************************************************************
     -- Chassis Security Settings
     -- ********************************************************************************
     chassisSecuritySettings        OBJECT IDENTIFIER ::= { securitySettings 5 }

      securityPolicySetting OBJECT-TYPE
                   SYNTAX  INTEGER {
                     legacy(0),
                     secure(1),
                     unknown(255)
                   }
                   ACCESS  read-write
                   STATUS  mandatory
                   DESCRIPTION
                   "Determines chassis security policy. legacy mode(0) or secure mode(1).
                   unknown(255) returned when policy can't be set or determined."
                   ::= { chassisSecuritySettings 1 }

      securityPolicyState OBJECT-TYPE
                   SYNTAX  INTEGER {
                     active(0),
                     pending(1),
                     unknown(255)
                   }
                   ACCESS  read-only
                   STATUS  mandatory
                   DESCRIPTION
                   "Determines chassis security policy state. If pending(0),
                   check securityPolicyStatusTable for details on actions needed,
                   to make fully active."
                   ::= { chassisSecuritySettings 2 }

      securityPolicyStatusTable OBJECT-TYPE
                    SYNTAX  SEQUENCE OF SecurityPolicyStatusEntry
                    ACCESS  not-accessible
                    STATUS  mandatory
                    DESCRIPTION
                    "Table of pending security policy status."
                    ::= { chassisSecuritySettings 3 }

      securityPolicyStatusEntry OBJECT-TYPE
                     SYNTAX SecurityPolicyStatusEntry
                     ACCESS  not-accessible
                     STATUS  mandatory
                     DESCRIPTION
                     "Pending security policy status entry"
                     INDEX { securityPolicyStatusIndex  }
                     ::= { securityPolicyStatusTable 1 }

      SecurityPolicyStatusEntry ::= SEQUENCE {
                   securityPolicyStatusIndex  INTEGER,
                   securityPolicyStatusComponentType  INTEGER,
                   securityPolicyStatusBayId  INTEGER,
                   securityPolicyStatusSummary  OCTET STRING,
                   securityPolicyStatusDetails  OCTET STRING
                   }

      securityPolicyStatusIndex OBJECT-TYPE
                   SYNTAX  INTEGER (0..128)
                   ACCESS  read-only
                   STATUS  mandatory
                   DESCRIPTION
                   "Pending Security policy status index."
                   ::= { securityPolicyStatusEntry 1 }

      securityPolicyStatusComponentType     OBJECT-TYPE
                   SYNTAX  INTEGER {
                     system(0),
                     mgmtModule1(1),
                     mgmtModule2(2),
                     blade1(11),
                     blade2(12),
                     blade3(13),
                     blade4(14),
                     blade5(15),
                     blade6(16),
                     blade7(17),
                     blade8(18),
                     blade9(19),
                     blade10(20),
                     blade11(21),
                     blade12(22),
                     blade13(23),
                     blade14(24),
                     switchModule1(31),
                     switchModule2(32),
                     switchModule3(33),
                     switchModule4(34)
                   }
                   ACCESS  read-only
                   STATUS  mandatory
                   DESCRIPTION
                   "Indicates Component type and location with pending security status."
                   ::= { securityPolicyStatusEntry 2 }

      securityPolicyStatusBayId OBJECT-TYPE
                   SYNTAX  INTEGER (0..14)
                   ACCESS  read-only
                   STATUS  mandatory
                   DESCRIPTION
                   "Bay location of specific component.
                   NOTE:  securityPolicyStatusComponentType enumeration also indicates location."
                   ::= { securityPolicyStatusEntry 3 }

      securityPolicyStatusSummary  OBJECT-TYPE
                   SYNTAX  OCTET STRING
                   ACCESS  read-only
                   STATUS  mandatory
                   DESCRIPTION
                   "Summary of pending security status for the component."
                   ::= { securityPolicyStatusEntry 4 }

      securityPolicyStatusDetails  OBJECT-TYPE
                   SYNTAX  OCTET STRING
                   ACCESS  read-only
                   STATUS  mandatory
                   DESCRIPTION
                   "Details of pending security status for the component."
                   ::= { securityPolicyStatusEntry 5 }

     cryptography        OBJECT IDENTIFIER ::= { chassisSecuritySettings 10 }

     cryptographySummary OBJECT-TYPE
                   SYNTAX OCTET STRING
                   ACCESS read-only
                   STATUS mandatory
                   DESCRIPTION
                   "The current level and summary description of the cryptographic configuration."
                   ::= { cryptography 5 }

     cryptographyMode OBJECT-TYPE
                   SYNTAX INTEGER {
                        nistCompatibility(0),
                        nist800131a(1)
                        }
                   ACCESS read-write
                   STATUS mandatory
                   DESCRIPTION
                   "The NIST cryptographic mode setting. A successful setting of this object
                    initiates a reboot of the CMM within a few seconds."
                   ::= { cryptography 15 }

      cryptographyModeDetailsTable OBJECT-TYPE
                    SYNTAX  SEQUENCE OF CryptographyModeDetailsEntry
                    ACCESS  not-accessible
                    STATUS  mandatory
                    DESCRIPTION
                    "A table of information indicating any NIST customization details
                     and any reasons that the CMM cannot transition to the desired
                     NIST mode."
                    ::= { cryptography 18 }

      cryptographyModeDetailsEntry OBJECT-TYPE
                     SYNTAX CryptographyModeDetailsEntry
                     ACCESS  not-accessible
                     STATUS  mandatory
                     DESCRIPTION
                     "Cryptography mode status entry"
                     INDEX { cryptographyModeDetailsIndex  }
                     ::= { cryptographyModeDetailsTable 1 }

      CryptographyModeDetailsEntry ::= SEQUENCE {
                   cryptographyModeDetailsIndex  INTEGER,
                   cryptographyModeDetailsType  INTEGER,
                   cryptographyModeDetailsDescription  OCTET STRING
                   }

      cryptographyModeDetailsIndex OBJECT-TYPE
                   SYNTAX  INTEGER
                   ACCESS  read-only
                   STATUS  mandatory
                   DESCRIPTION
                   "Cryptography mode details index."
                   ::= { cryptographyModeDetailsEntry 1 }

      cryptographyModeDetailsType     OBJECT-TYPE
                   SYNTAX  INTEGER {
                     customization(0),
                     transition(1)
                   }
                   ACCESS  read-only
                   STATUS  mandatory
                   DESCRIPTION
                   "Indication of what type of message is reported for this entry."
                   ::= { cryptographyModeDetailsEntry 2 }

      cryptographyModeDetailsDescription  OBJECT-TYPE
                   SYNTAX  OCTET STRING
                   ACCESS  read-only
                   STATUS  mandatory
                   DESCRIPTION
                   "Message containing details for this cryptography entry."
                   ::= { cryptographyModeDetailsEntry 3 }

      cryptographyModeComponentTable OBJECT-TYPE
                    SYNTAX  SEQUENCE OF CryptographyModeComponentEntry
                    ACCESS  not-accessible
                    STATUS  mandatory
                    DESCRIPTION
                    "A table of information listing any IOMs or nodes that require a
                     firmware update in order for the CMM to transition to the new mode."
                    ::= { cryptography 20 }

      cryptographyModeComponentEntry OBJECT-TYPE
                     SYNTAX CryptographyModeComponentEntry
                     ACCESS  not-accessible
                     STATUS  mandatory
                     DESCRIPTION
                     "Cryptography mode component entry"
                     INDEX { cryptographyModeComponentIndex  }
                     ::= { cryptographyModeComponentTable 1 }

      CryptographyModeComponentEntry ::= SEQUENCE {
                   cryptographyModeComponentIndex  INTEGER,
                   cryptographyModeComponentId  OCTET STRING
                   }

      cryptographyModeComponentIndex OBJECT-TYPE
                   SYNTAX  INTEGER
                   ACCESS  read-only
                   STATUS  mandatory
                   DESCRIPTION
                   "Cryptography mode component index."
                   ::= { cryptographyModeComponentEntry 1 }

      cryptographyModeComponentId  OBJECT-TYPE
                   SYNTAX  OCTET STRING
                   ACCESS  read-only
                   STATUS  mandatory
                   DESCRIPTION
                   "A component identifier for an IOM or node in the form:
                    ts:mm.  t(type), s(slot number), mm sub-slot number."
                   ::= { cryptographyModeComponentEntry 2 }

      cryptographicCipher OBJECT-TYPE
                   SYNTAX  INTEGER {
                     legacy(0),
                     tls12serveronly(1),
                     tls12serverclient(2)
                   }
                   ACCESS  read-write
                   STATUS  mandatory
                   DESCRIPTION
                   "The cryptographic cipher suite setting."
                   ::= { cryptography 25 }

      cryptographyCipherComponentTable OBJECT-TYPE
                    SYNTAX  SEQUENCE OF CryptographyCipherComponentEntry
                    ACCESS  not-accessible
                    STATUS  mandatory
                    DESCRIPTION
                    "A table of information listing any IOMs or nodes that are out of
                     compliance with regards to the cipher suite setting and are therefore
                     preventing the CMM from transitioning to the new cipher mode."
                    ::= { cryptography 30 }

      cryptographyCipherComponentEntry OBJECT-TYPE
                     SYNTAX CryptographyCipherComponentEntry
                     ACCESS  not-accessible
                     STATUS  mandatory
                     DESCRIPTION
                     "Cryptography cipher component entry"
                     INDEX { cryptographyCipherComponentIndex  }
                     ::= { cryptographyCipherComponentTable 1 }

      CryptographyCipherComponentEntry ::= SEQUENCE {
                   cryptographyCipherComponentIndex  INTEGER,
                   cryptographyCipherComponentId  OCTET STRING
                   }

      cryptographyCipherComponentIndex OBJECT-TYPE
                   SYNTAX  INTEGER
                   ACCESS  read-only
                   STATUS  mandatory
                   DESCRIPTION
                   "Cryptography cipher component index."
                   ::= { cryptographyCipherComponentEntry 1 }

      cryptographyCipherComponentId  OBJECT-TYPE
                   SYNTAX  OCTET STRING
                   ACCESS  read-only
                   STATUS  mandatory
                   DESCRIPTION
                   "A component identifier for an IOM or node in the form:
                    ts:mm.  t(type), s(slot number), mm sub-slot number."
                   ::= { cryptographyCipherComponentEntry 2 }

      cipherStrength OBJECT-TYPE
                   SYNTAX  INTEGER {
                     none(0),
                     rsa2048SHA1(1),
                     rsa2048SHA256(2)
                   }
                   ACCESS  read-write
                   STATUS  mandatory
                   DESCRIPTION
                   "Strength level of the NIST signing algorithm for certificate authority.
                   None(0) indicates no signing algorithm has been set. When writing a new
                   value to this object, a result of No Error is returned if the value is
                   valid.  However, the new algorithm will be used to create an authority
                   certificate asynchronously.  This process may take up to 1 minute to complete.
                   So results for subsequent queries to the object's value may also be delayed
                   while the new certificate is being generated."
                   ::= { chassisSecuritySettings 15 }
      -- ********************************************************************************
      -- MM Clock
      -- ********************************************************************************
      spClock        OBJECT IDENTIFIER ::= { configureSP 4 }

       spClockDateAndTimeSetting OBJECT-TYPE
                    SYNTAX  OCTET STRING
                    ACCESS  read-write
                    STATUS  mandatory
                    DESCRIPTION
                    "MM clock date and time setting.
                    A date-time specification for the local time of day.
                    For example to set the date and time to
                    March 4, 2001 at 06:00:00AM, set the value to:'03/04/2001,06:00:00'.
                    field  contents         range
                    _____  ________         _____
                      1     month           01..12
                      2     separator       '/'
                      3     day             01..31
                      4     separator       '/'
                      5     year            2000..2089
                      6     separator       ','
                      7     hour            00..23
                      8     separator       ':'
                      9     minutes         00..59
                      10    separator       ':'
                      11    seconds         00..59
                    "
                    ::= { spClock  1 }

       spClockTimezoneSetting OBJECT-TYPE
                    SYNTAX  OCTET STRING
                    ACCESS  read-write
                    STATUS  mandatory
                    DESCRIPTION
                    "MM clock Greenwich Mean Time(GMT) offset and Daylight Saving Time(DST)
                    settings.

                    For write, the value must be a time zone listed in spClockTimezoneTable.
                    The spClockTimezoneTable lists all valid time zones.
                    Example:
                     To set America's New York time zone, set the value to: 'America/New_York'

                    For read, the value format is <offset>,<DST flag>,<time zone> (<comment>)
                    Example: -4:00,yes,America/New_York (Eastern Time)
                    "
                    ::= { spClock  2 }

        spClockTimezoneTable OBJECT-TYPE
                    SYNTAX  SEQUENCE OF SpClockTimezoneEntry
                    ACCESS  not-accessible
                    STATUS  mandatory
                    DESCRIPTION
                    "Table of all time zones listed in zone.tab file"
                    ::= { spClock 3 }

        spClockTimezoneEntry OBJECT-TYPE
                     SYNTAX SpClockTimezoneEntry
                     ACCESS  not-accessible
                     STATUS  mandatory
                     DESCRIPTION
                     "Time zone entry"
                     INDEX { spClockTimezoneIndex  }
                     ::= { spClockTimezoneTable 1 }

        SpClockTimezoneEntry ::= SEQUENCE {
                   spClockTimezoneIndex    INTEGER,
                   spClockTimezoneId       OCTET STRING,
                   spClockTimezoneCaption  OCTET STRING,
                   spClockTimezoneDescription OCTET STRING,
                   spClockTimezoneName        OCTET STRING,
                   spClockTimezoneStandardName OCTET STRING,
                   spClockTimezoneStandardCaption OCTET STRING,
                   spClockTimezoneDaylightName    OCTET STRING,
                   spClockTimezoneDaylightCaption OCTET STRING,
                   spClockTimezoneCmmOffset       INTEGER,
                   spClockTimezoneStandardOffsetMinutes INTEGER,
                   spClockTimezoneStandardDaylightOffsetMinutes INTEGER,
                   spClockTimezoneDaylightDay INTEGER,
                   spClockTimezoneDaylightDayOfWeek INTEGER,
		   spClockTimezoneDaylightMonth INTEGER,
                   spClockTimezoneDaylightStandardDay INTEGER,
                   spClockTimezoneDaylightStandardDayOfWeek INTEGER,
                   spClockTimezoneDaylightStandardMonth INTEGER,
                   spClockTimezoneDaylightIntervalInMinutes INTEGER,
                   spClockTimezoneDaylightStandardInMinutes INTEGER
                   }

        spClockTimezoneIndex OBJECT-TYPE
                   SYNTAX  INTEGER (0..1000)
                   ACCESS  read-only
                   STATUS  mandatory
                   DESCRIPTION
                   "Time zone table index."
                   ::= { spClockTimezoneEntry 1 }

        spClockTimezoneId  OBJECT-TYPE
                   SYNTAX  OCTET STRING
                   ACCESS  read-only
                   STATUS  mandatory
                   DESCRIPTION
                   "Time zone instance id."
                   ::= { spClockTimezoneEntry 2 }

        spClockTimezoneCaption   OBJECT-TYPE
                   SYNTAX  OCTET STRING
                   ACCESS  read-only
                   STATUS  mandatory
                   DESCRIPTION
                   "Time zone caption."
                   ::= { spClockTimezoneEntry 3 }

        spClockTimezoneDescription   OBJECT-TYPE
                   SYNTAX  OCTET STRING
                   ACCESS  read-only
                   STATUS  mandatory
                   DESCRIPTION
                   "Time zone description."
                   ::= { spClockTimezoneEntry 4 }

	spClockTimezoneName    OBJECT-TYPE
                   SYNTAX  OCTET STRING
                   ACCESS  read-only
                   STATUS  mandatory
                   DESCRIPTION
                   "Time zone name."
                   ::= { spClockTimezoneEntry 5 }

         spClockTimezoneStandardName OBJECT-TYPE
                   SYNTAX  OCTET STRING
                   ACCESS  read-only
                   STATUS  mandatory
                   DESCRIPTION
                   "Time zone standard name."
                   ::= { spClockTimezoneEntry 6 }

         spClockTimezoneStandardCaption OBJECT-TYPE
                   SYNTAX  OCTET STRING
                   ACCESS  read-only
                   STATUS  mandatory
                   DESCRIPTION
                   "Time zone standard caption."
                   ::= { spClockTimezoneEntry 7 }

          spClockTimezoneDaylightName OBJECT-TYPE
                   SYNTAX  OCTET STRING
                   ACCESS  read-only
                   STATUS  mandatory
                   DESCRIPTION
                   "Time zone daylight name."
                   ::= { spClockTimezoneEntry 8 }

	   spClockTimezoneDaylightCaption OBJECT-TYPE
                   SYNTAX  OCTET STRING
                   ACCESS  read-only
                   STATUS  mandatory
                   DESCRIPTION
                   "Time zone daylight caption."
                   ::= { spClockTimezoneEntry 9 }

           spClockTimezoneCmmOffset OBJECT-TYPE
                   SYNTAX  INTEGER
                   ACCESS  read-only
                   STATUS  mandatory
                   DESCRIPTION
                   "CMM offset."
                   ::= { spClockTimezoneEntry 10 }

	   spClockTimezoneStandardOffsetMinutes OBJECT-TYPE
                   SYNTAX  INTEGER
                   ACCESS  read-only
                   STATUS  mandatory
                   DESCRIPTION
                   "Standard GMT offset in minutes."
                   ::= { spClockTimezoneEntry 11 }

            spClockTimezoneStandardDaylightOffsetMinutes OBJECT-TYPE
                   SYNTAX  INTEGER
                   ACCESS  read-only
                   STATUS  mandatory
                   DESCRIPTION
                   "Standard GMT offset in minutes."
                   ::= { spClockTimezoneEntry 12 }

	    spClockTimezoneDaylightDay OBJECT-TYPE
                   SYNTAX  INTEGER{
                     undefined(255)
                   }
                   ACCESS  read-only
                   STATUS  mandatory
                   DESCRIPTION
                   "There are two different interpretations for this field, depending on the value of DaylightDayOfWeek.
                    In one case, DaylightDay defines the day-in-month on which daylight saving time starts.
                    This interpretation is used when the DaylightDayOfWeek is 0.
                    A positive or negative integer is specified to indicate whether the DaylightDay is calculated
                    from the beginning or the end of the month.


                    For example, 5 indicates the fifth day in the DaylightMonth and -1 indicates the last day in the DaylightMonth.


	            When DaylightDayOfWeek is not 0, DaylightDay is the day in the month on which daylight saving time starts,
                    as defined in conjunction with DaylightDayOfWeek.
                    For example, if DaylightDay is 15 and DaylightDayOfWeek is Saturday, then daylight saving time starts
                    on the first Saturday on or after the 15th day in the DaylightMonth (that is, the third Saturday in the month).


                    If DaylightDay is 20 and DaylightDayOfWeek is -Saturday, then this indicates the first Saturday on or before
                    the 20th day in the DaylightMonth.
                    If DaylightDay is -1 and DaylightDayOfWeek is -Sunday, then this indicates the last Sunday in the month."

                    ::= { spClockTimezoneEntry 13 }

            spClockTimezoneDaylightDayOfWeek OBJECT-TYPE
                   SYNTAX  INTEGER{
                        exactDayOfMonth(0),
                        minusSunday(-1),
                        minusMonday(-2),
                        minusTuesday(-3),
                        minusWednesday(-4),
                        minusThursday(-5),
                        minusFriday(-6),
                        minusSaturday(-7),
                        sunday(1),
                        monday(2),
                        tuesday(3),
                        wednesday(4),
                        thursday(5),
                        friday(6),
                        saturday(7),
                        undefined(255)
                   }
                   ACCESS  read-only
                   STATUS  mandatory
                   DESCRIPTION
                   "Day of week daylight saving begins."
                   ::= { spClockTimezoneEntry 14 }

	    spClockTimezoneDaylightMonth OBJECT-TYPE
                   SYNTAX  INTEGER{
                        january(0),
                        february(1),
                        march(2),
                        april(3),
                        may(4),
                        june(5),
                        july(6),
                        august(7),
                        september(8),
                        october(9),
                        november(10),
                        december(11),
                        undefined(255)
		   }
                   ACCESS  read-only
                   STATUS  mandatory
                   DESCRIPTION
                   "Month daylight saving begins."
                   ::= { spClockTimezoneEntry 15 }

             spClockTimezoneDaylightStandardDay OBJECT-TYPE
                   SYNTAX  INTEGER{
                     undefined(255)
                   }
                   ACCESS  read-only
                   STATUS  mandatory
                   DESCRIPTION
                   "There are two different interpretations for this property, depending on the value of StandardDayOfWeek.
                    In one case, StandardDay defines the day-in-month on which daylight saving time ends. This interpretation
                    is used when the StandardDayOfWeek is 0.
                    A positive or negative integer is specified to indicate whether the StandardDay is calculated from the beginning or                                        the end of the month.


                    For example, 5 indicates the fifth day in the StandardMonth and -1 indicates the last day in the StandardMonth.
                    When StandardDayOfWeek is not 0, StandardDay is the day-in-month on which daylight saving time ends, as defined in
                    conjunction with StandardDayOfWeek.


                    For example, if StandardDay is 15 and StandardDayOfWeek is Saturday,
                    then daylight saving time ends on the first Saturday on or after the 15th day in the StandardMonth (that is,
                    the third Saturday in the month).


                    If StandardDay is 20 and StandardDayOfWeek is -Saturday, then this indicates the first Saturday on or before the 20
                    th day in the StandardMonth.
                    If StandardDay is -1 and StandardDayOfWeek is -Sunday, then this indicates the last Sunday in the StandardMonth."

                  ::= { spClockTimezoneEntry 16 }

              spClockTimezoneDaylightStandardDayOfWeek OBJECT-TYPE
                   SYNTAX  INTEGER{
                        exactDayOfMonth(0),
                        minusSunday(-1),
                        minusMonday(-2),
                        minusTuesday(-3),
                        minusWednesday(-4),
                        minusThursday(-5),
                        minusFriday(-6),
                        minusSaturday(-7),
                        sunday(1),
                        monday(2),
                        tuesday(3),
                        wednesday(4),
                        thursday(5),
                        friday(6),
                        saturday(7),
                        undefined(255)

                   }
                   ACCESS  read-only
                   STATUS  mandatory
                   DESCRIPTION
                   "Day of week daylight saving ends."
                   ::= { spClockTimezoneEntry 17 }

             spClockTimezoneDaylightStandardMonth OBJECT-TYPE
                   SYNTAX  INTEGER{
                        january(0),
                        february(1),
                        march(2),
                        april(3),
                        may(4),
                        june(5),
                        july(6),
                        august(7),
                        september(8),
                        october(9),
                        november(10),
                        december(11),
                        undefined(255)
                   }
                   ACCESS  read-only
                   STATUS  mandatory
                   DESCRIPTION
                   "Month daylight saving ends."
                   ::= { spClockTimezoneEntry 18 }

	     spClockTimezoneDaylightIntervalInMinutes  OBJECT-TYPE
                   SYNTAX  INTEGER
                   ACCESS  read-only
                   STATUS  mandatory
                   DESCRIPTION
                   "Interval in minutes (Daylight saving begins)."
                   ::= { spClockTimezoneEntry 19 }

             spClockTimezoneDaylightStandardInMinutes OBJECT-TYPE
                   SYNTAX  INTEGER
                   ACCESS  read-only
                   STATUS  mandatory
                   DESCRIPTION
                   "Interval in minutes (Daylight saving ends)."
                   ::= { spClockTimezoneEntry 20 }



              spClockTimezoneDaylightStart OBJECT-TYPE
                    SYNTAX  OCTET STRING
                    ACCESS  read-only
                    STATUS  mandatory
                    DESCRIPTION
                    "DST start."
                    ::= { spClock  5 }
	      spClockTimezoneDaylightEnd OBJECT-TYPE
                    SYNTAX  OCTET STRING
                    ACCESS  read-only
                    STATUS  mandatory
                    DESCRIPTION
                    "DST end."
                    ::= { spClock  6 }


      -- ********************************************************************************
      -- MM identification
      -- ********************************************************************************
      spIdentification        OBJECT IDENTIFIER ::= { configureSP 5 }

       spTxtId      OBJECT-TYPE
                    SYNTAX  OCTET STRING (SIZE(0..16))
                    ACCESS  read-write
                    STATUS  mandatory
                    DESCRIPTION
                    "Text description of the MM.
                    NOTE: Do not put any 'space characters' at end of the string."
                    ::= { spIdentification 1 }

      -- ********************************************************************************
      -- Network Configuration
      -- ********************************************************************************
      networkConfiguration  OBJECT IDENTIFIER ::= { configureSP 9 }

       -- ********************************************************************************
       -- Network Interfaces
       -- ********************************************************************************
       networkInterfaces  OBJECT IDENTIFIER ::= { networkConfiguration 1 }

        -- ********************************************************************************
        -- Ethernet Interface
        -- ********************************************************************************
        extEthernetInterface  OBJECT IDENTIFIER ::= { networkInterfaces 1 }

         extEthernetInterfaceType OBJECT-TYPE
                      SYNTAX  OCTET STRING (SIZE(0..16))
                      ACCESS  read-only
                      STATUS  mandatory
                      DESCRIPTION
                      "The type of interface."
                      ::= { extEthernetInterface 1 }

         extEthernetInterfaceHostName  OBJECT-TYPE
                      SYNTAX  OCTET STRING (SIZE(0..64))
                      ACCESS  read-write
                      STATUS  mandatory
                      DESCRIPTION
                      "Contains the 64 byte null terminated DNS host name for this
                      interface."
                      ::= { extEthernetInterface 3 }

         extEthernetInterfaceIPAddress   OBJECT-TYPE
                      SYNTAX  IpAddress
                      ACCESS  read-write
                      STATUS  mandatory
                      DESCRIPTION
                      "Contains the IP address for the ethernet interface."
                      ::= { extEthernetInterface 4 }

         extEthernetInterfaceDataRate   OBJECT-TYPE
                      SYNTAX  INTEGER {
                        enet10Megabit(3),
                        enet100Megabit(4),
                        autoSpeed(5),
                        enet1Gigabit(6)
                      }
                      ACCESS  read-write
                      STATUS  mandatory
                      DESCRIPTION
                      "Specifies the data transfer rate to be used over the ethernet
                      interface:  10Mb, 100Mb, 1G or Auto."
                      ::= { extEthernetInterface 5 }

         extEthernetInterfaceDuplexSetting  OBJECT-TYPE
                      SYNTAX  INTEGER {
                        fullDuplex(1),
                        halfDuplex(2),
                        autoDuplex(3)
                      }
                      ACCESS  read-write
                      STATUS  mandatory
                      DESCRIPTION
                      "Specifies the duplex settings for the data transfer rate to be used over
                      the ethernet interface:  Half, Full, or Auto."
                      ::= { extEthernetInterface 6 }

         extEthernetInterfaceLAA OBJECT-TYPE
                      SYNTAX  OCTET STRING (SIZE(17))
                      ACCESS  read-write
                      STATUS  mandatory
                      DESCRIPTION
                      "Specifies the locally administered MAC address.  The locally administered
                      address must be a hexadecimal value between 000000000000 - FFFFFFFFFFFF.  This
                      value must be in the form XX:XX:XX:XX:XX:XX where 'X' is a number between 0 - 9 and
                      A - F.  This MM subsystem does not allow use of a multicast address.  A multicast
                      address has the least significant bit of the first byte set to a 1.  The first
                      byte must, therefore, be an even number.

                      NOTE: Although the locally administered MAC address can be assigned the same value
                      for the primary and backup MM, it is not recommended."
                      ::= { extEthernetInterface 7 }

         extEthernetInterfaceDhcpEnabled  OBJECT-TYPE
                      SYNTAX  INTEGER {
                        dhcpDisabled(0),
                        dhcpEnabled(1),
                        tryDhcpThenTryStatic(2)
                      }
                      ACCESS  read-write
                      STATUS  mandatory
                      DESCRIPTION
                      "Disable or enable DHCP on this interface."
                      ::= { extEthernetInterface 8 }

         extEthernetInterfaceGatewayIPAddress   OBJECT-TYPE
                      SYNTAX  IpAddress
                      ACCESS  read-write
                      STATUS  mandatory
                      DESCRIPTION
                      "Contains the IP address of the gateway/router for the ethernet
                       interface."
                      ::= { extEthernetInterface 9 }

         extEthernetInterfaceBIA OBJECT-TYPE
                      SYNTAX  OCTET STRING (SIZE(17))
                      ACCESS  read-only
                      STATUS  mandatory
                      DESCRIPTION
                      "Specifies the burned-in MAC (BIA) address."
                      ::= { extEthernetInterface 10 }

         extEthernetInterfaceMTU   OBJECT-TYPE
                      SYNTAX  INTEGER
                      ACCESS  read-write
                      STATUS  mandatory
                      DESCRIPTION
                      "Contains the Maximum Transmission Unit(MTU) for the ethernet
                      interface"
                      ::= { extEthernetInterface 13 }

         extEthernetInterfaceSubnetMask   OBJECT-TYPE
                      SYNTAX  IpAddress
                      ACCESS  read-write
                      STATUS  mandatory
                      DESCRIPTION
                      "Contains the subnet mask for the ethernet interface"
                      ::= { extEthernetInterface 14 }

          extEthernetInterfaceFloatingIPAddress   OBJECT-TYPE
                       SYNTAX  IpAddress
                       ACCESS  read-write
                       STATUS  mandatory
                       DESCRIPTION
                       "Contains the floating IP address for the external ethernet interface."
                       ::= { extEthernetInterface 22 }

         -- ********************************************************************************
         -- DHCP Server Assigned Settings for ethernet interface 
         -- ********************************************************************************

         dhcpEthernetInterface  OBJECT IDENTIFIER ::= { extEthernetInterface 16 }

          dhcpHostName  OBJECT-TYPE
                       SYNTAX  OCTET STRING (SIZE(0..64))
                       ACCESS  read-only
                       STATUS  mandatory
                       DESCRIPTION
                       "Contains the 64 byte null terminated DNS host name for this
                       interface, assigned by the DHCP server."
                       ::= { dhcpEthernetInterface 1 }

          dhcpIPAddress   OBJECT-TYPE
                       SYNTAX  IpAddress
                       ACCESS  read-only
                       STATUS  mandatory
                       DESCRIPTION
                       "Contains the IP address for the ethernet interface,
                       assigned by the DHCP server."
                       ::= { dhcpEthernetInterface 2 }

          dhcpGatewayIPAddress   OBJECT-TYPE
                       SYNTAX  IpAddress
                       ACCESS  read-only
                       STATUS  mandatory
                       DESCRIPTION
                       "Contains the IP address of the gateway/router for the ethernet
                        interface, assigned by the DHCP server."
                       ::= { dhcpEthernetInterface 3 }

          dhcpSubnetMask   OBJECT-TYPE
                       SYNTAX  IpAddress
                       ACCESS  read-only
                       STATUS  mandatory
                       DESCRIPTION
                       "Contains the Subnet Mask for the ethernet
                       interface, assigned by the DHCP server."
                       ::= { dhcpEthernetInterface 4 }

          dhcpDomainName  OBJECT-TYPE
                       SYNTAX  OCTET STRING (SIZE(0..64))
                       ACCESS  read-only
                       STATUS  mandatory
                       DESCRIPTION
                       "Contains the 64 byte null terminated Domain Name for this
                       interface, assigned by the DHCP server."
                       ::= { dhcpEthernetInterface 5 }

          dhcpDHCPServer  OBJECT-TYPE
                       SYNTAX  IpAddress
                       ACCESS  read-only
                       STATUS  mandatory
                       DESCRIPTION
                       "Contains the DHCP server IP address used to acquire the
                       DHCP settings."
                       ::= { dhcpEthernetInterface 6 }

          dhcpPrimaryDNSServer  OBJECT-TYPE
                       SYNTAX  IpAddress
                       ACCESS  read-only
                       STATUS  mandatory
                       DESCRIPTION
                       "Contains the Primary DNS server, assigned by the DHCP server."
                       ::= { dhcpEthernetInterface 7 }

          dhcpSecondaryDNSServer  OBJECT-TYPE
                       SYNTAX  IpAddress
                       ACCESS  read-only
                       STATUS  mandatory
                       DESCRIPTION
                       "Contains the Secondary DNS server, assigned by the DHCP server."
                       ::= { dhcpEthernetInterface 8 }

          dhcpTertiaryDNSServer  OBJECT-TYPE
                       SYNTAX  IpAddress
                       ACCESS  read-only
                       STATUS  mandatory
                       DESCRIPTION
                       "Contains the tertiary DNS server, assigned by the DHCP server."
                       ::= { dhcpEthernetInterface 9 }

         -- ********************************************************************************
        -- Standby Ethernet Interface
        -- ********************************************************************************
         standbyExtEthernetInterface  OBJECT IDENTIFIER ::= { networkInterfaces 3 }
         standbyExtEthernetInterfaceType OBJECT-TYPE
                      SYNTAX  OCTET STRING (SIZE(0..16))
                      ACCESS  read-only
                      STATUS  mandatory
                      DESCRIPTION
                      "The type of interface.

                      NOTE: This MIB object is only applicable to systems with a standby MM."
                      ::= { standbyExtEthernetInterface 1 }

         standbyExtEthernetInterfaceHostName  OBJECT-TYPE
                      SYNTAX  OCTET STRING (SIZE(0..64))
                      ACCESS  read-write
                      STATUS  mandatory
                      DESCRIPTION
                      "Contains the 64 byte null terminated DNS host name for this
                      interface.

                      NOTE: This MIB object is only applicable to systems with a standby MM."
                      ::= { standbyExtEthernetInterface 3 }

         standbyExtEthernetInterfaceIPAddress   OBJECT-TYPE
                      SYNTAX  IpAddress
                      ACCESS  read-write
                      STATUS  mandatory
                      DESCRIPTION
                      "Contains the IP address for the ethernet interface.

                      NOTE: This MIB object is only applicable to systems with a standby MM."
                      ::= { standbyExtEthernetInterface 4 }

         standbyExtEthernetInterfaceDataRate   OBJECT-TYPE
                      SYNTAX  INTEGER {
                        enet10Megabit(3),
                        enet100Megabit(4),
                        autoSpeed(5),
                        enet1Gigabit(6)
                      }
                      ACCESS  read-write
                      STATUS  mandatory
                      DESCRIPTION
                      "Specifies the data transfer rate to be used over the ethernet
                      interface:  10Mb, 100Mb, 1G or Auto.

                      NOTE: This MIB object is only applicable to systems with a standby MM."
                      ::= { standbyExtEthernetInterface 5 }

         standbyExtEthernetInterfaceDuplexSetting  OBJECT-TYPE
                      SYNTAX  INTEGER {
                        fullDuplex(1),
                        halfDuplex(2),
                        autoDuplex(3)
                      }
                      ACCESS  read-write
                      STATUS  mandatory
                      DESCRIPTION
                      "Specifies the duplex settings for the data transfer rate to be used over
                      the ethernet interface:  Half, Full, or Auto.

                      NOTE: This MIB object is only applicable to systems with a standby MM."
                      ::= { standbyExtEthernetInterface 6 }

         standbyExtEthernetInterfaceLAA OBJECT-TYPE
                      SYNTAX  OCTET STRING (SIZE(17))
                      ACCESS  read-write
                      STATUS  mandatory
                      DESCRIPTION
                      "Specifies the locally administered MAC address.  The locally administered
                      address must be a hexadecimal value between 000000000000 - FFFFFFFFFFFF.
                      This value must be in the form XX:XX:XX:XX:XX:XX where 'X' is a number between 0 - 9 and A - F.
                      This MM subsystem does not allow use of a multicast address.
                      A multicast address has the least significant bit of the first byte set to a 1.  The first
                      byte must, therefore, be an even number.

                      NOTE: This MIB object is only applicable to systems with a standby MM.
                      NOTE: Although the locally administered MAC address can be assigned the same value
                      for the primary and backup MM, it is not recommended."
                      ::= { standbyExtEthernetInterface 7 }

         standbyExtEthernetInterfaceDhcpEnabled  OBJECT-TYPE
                      SYNTAX  INTEGER {
                        dhcpDisabled(0),
                        dhcpEnabled(1),
                        tryDhcpThenTryStatic(2)
                      }
                      ACCESS  read-write
                      STATUS  mandatory
                      DESCRIPTION
                      "Disable or enable DHCP on this interface.

                      NOTE: This MIB object is only applicable to systems with a standby MM."
                      ::= { standbyExtEthernetInterface 8 }

         standbyExtEthernetInterfaceGatewayIPAddress   OBJECT-TYPE
                      SYNTAX  IpAddress
                      ACCESS  read-write
                      STATUS  mandatory
                      DESCRIPTION
                      "Contains the IP address of the gateway/router for the ethernet
                       interface.

                      NOTE: This MIB object is only applicable to systems with a standby MM."
                      ::= { standbyExtEthernetInterface 9 }

         standbyExtEthernetInterfaceBIA OBJECT-TYPE
                      SYNTAX  OCTET STRING (SIZE(17))
                      ACCESS  read-only
                      STATUS  mandatory
                      DESCRIPTION
                      "Specifies the burned-in MAC (BIA) address.

                      NOTE: This MIB object is only applicable to systems with a standby MM."
                      ::= { standbyExtEthernetInterface 10 }

         standbyExtEthernetInterfaceMTU   OBJECT-TYPE
                      SYNTAX  INTEGER
                      ACCESS  read-write
                      STATUS  mandatory
                      DESCRIPTION
                      "Contains the Maximum Transmission Unit (MTU) for the ethernet
                      interface.

                      NOTE: This MIB object is only applicable to systems with a standby MM."
                      ::= { standbyExtEthernetInterface 13 }

         standbyExtEthernetInterfaceSubnetMask   OBJECT-TYPE
                      SYNTAX  IpAddress
                      ACCESS  read-write
                      STATUS  mandatory
                      DESCRIPTION
                      "Contains the subnet mask for the ethernet interface.

                      NOTE: This MIB object is only applicable to systems with a standby MM."
                      ::= { standbyExtEthernetInterface 14 }

         advancedFailover  OBJECT-TYPE
                      SYNTAX  INTEGER{
                        off(0),
                        ipnoswap(1),
                        ipswap(2)
                      }
                      ACCESS  read-write
                      STATUS  mandatory
                      DESCRIPTION
                      "User can enable advanced failover.
                       off : no standby network interface
                       ipswap: Standby network interface, swap IPs during failover
                       ipnoswap: Standby network interface, do not swap IPs during failover.

                      NOTE: This MIB object is only applicable to systems with a standby MM."
                      ::= { standbyExtEthernetInterface 15 }

         -- ********************************************************************************
         -- DHCP Server Assigned Settings for standby ethernet interface
         -- ********************************************************************************

         standbyDhcpEthernetInterface  OBJECT IDENTIFIER ::= { standbyExtEthernetInterface 16 }

          standbyDhcpHostName  OBJECT-TYPE
                       SYNTAX  OCTET STRING (SIZE(0..64))
                       ACCESS  read-only
                       STATUS  mandatory
                       DESCRIPTION
                       "Contains the 64 byte null terminated DNS host name for this
                       interface, assigned by the DHCP server.

                       NOTE: This MIB object is only applicable to systems with a standby MM."
                       ::= { standbyDhcpEthernetInterface 1 }

          standbyDhcpIPAddress   OBJECT-TYPE
                       SYNTAX  IpAddress
                       ACCESS  read-only
                       STATUS  mandatory
                       DESCRIPTION
                       "Contains the IP address for the ethernet interface,
                       assigned by the DHCP server.

                       NOTE: This MIB object is only applicable to systems with a standby MM."
                       ::= { standbyDhcpEthernetInterface 2 }

          standbyDhcpGatewayIPAddress   OBJECT-TYPE
                       SYNTAX  IpAddress
                       ACCESS  read-only
                       STATUS  mandatory
                       DESCRIPTION
                       "Contains the IP address of the gateway/router for the ethernet
                        interface, assigned by the DHCP server.

                       NOTE: This MIB object is only applicable to systems with a standby MM."
                       ::= { standbyDhcpEthernetInterface 3 }

          standbyDhcpSubnetMask   OBJECT-TYPE
                       SYNTAX  IpAddress
                       ACCESS  read-only
                       STATUS  mandatory
                       DESCRIPTION
                       "Contains the Subnet Mask for the ethernet
                       interface, assigned by the DHCP server.

                       NOTE: This MIB object is only applicable to systems with a standby MM."
                       ::= { standbyDhcpEthernetInterface 4 }

          standbyDhcpDomainName  OBJECT-TYPE
                       SYNTAX  OCTET STRING (SIZE(0..64))
                       ACCESS  read-only
                       STATUS  mandatory
                       DESCRIPTION
                       "Contains the 64 byte null terminated Domain Name for this
                       interface, assigned by the DHCP server.

                       NOTE: This MIB object is only applicable to systems with a standby MM."
                       ::= { standbyDhcpEthernetInterface 5 }

          standbyDhcpDHCPServer  OBJECT-TYPE
                       SYNTAX  IpAddress
                       ACCESS  read-only
                       STATUS  mandatory
                       DESCRIPTION
                       "Contains the DHCP server IP address used to acquire the
                       DHCP settings.

                       NOTE: This MIB object is only applicable to systems with a standby MM."
                       ::= { standbyDhcpEthernetInterface 6 }

          standbyDhcpPrimaryDNSServer  OBJECT-TYPE
                       SYNTAX  IpAddress
                       ACCESS  read-only
                       STATUS  mandatory
                       DESCRIPTION
                       "Contains the Primary DNS server, assigned by the DHCP server.

                       NOTE: This MIB object is only applicable to systems with a standby MM."
                       ::= { standbyDhcpEthernetInterface 7 }

          standbyDhcpSecondaryDNSServer  OBJECT-TYPE
                       SYNTAX  IpAddress
                       ACCESS  read-only
                       STATUS  mandatory
                       DESCRIPTION
                       "Contains the Secondary DNS server, assigned by the DHCP server.

                       NOTE: This MIB object is only applicable to systems with a standby MM."
                       ::= { standbyDhcpEthernetInterface 8 }

          standbyDhcpTertiaryDNSServer  OBJECT-TYPE
                       SYNTAX  IpAddress
                       ACCESS  read-only
                       STATUS  mandatory
                       DESCRIPTION
                       "Contains the tertiary DNS server, assigned by the DHCP server.

                       NOTE: This MIB object is only applicable to systems with a standby MM."
                       ::= { standbyDhcpEthernetInterface 9 }

       -- ********************************************************************************
       -- Ethernet Interface IPv6
       -- ********************************************************************************
       extEthernetInterfaceIPv6  OBJECT IDENTIFIER ::= { networkInterfaces 4 }

        extEthernetInterfaceIPv6Type OBJECT-TYPE
                     SYNTAX  OCTET STRING (SIZE(0..16))
                     ACCESS  read-only
                     STATUS  mandatory
                     DESCRIPTION
                     "The type of interface."
                     ::= { extEthernetInterfaceIPv6 1 }

        extEthernetInterfaceIPv6Enabled  OBJECT-TYPE
                     SYNTAX  INTEGER {
                       enabled(1)
                     }
                     ACCESS  read-write
                     STATUS  mandatory
                     DESCRIPTION
                     "The current IPv6 enabled or disabled state of this MM.

                     NOTE: If IPv6 address(es) have been configured for one or more
                     interfaces/protocols/services on this MM, when you update
                     the firmware to a level which does not support IPv6, all IPv6
                     connectivity will be lost, and services/interfaces for which an IPv6
                     address was configured may not function properly. You will be required
                     to reconfigure these services/interfaces."
                     ::= { extEthernetInterfaceIPv6 2 }

        extEthernetInterfaceIPv6Config  OBJECT IDENTIFIER ::= { extEthernetInterfaceIPv6 5 }

        extEthernetInterfaceIPv6LocalAddress  OBJECT IDENTIFIER ::= { extEthernetInterfaceIPv6Config 1 }

         extEthernetInterfaceIPv6LinkLocalAddress  OBJECT-TYPE
                     SYNTAX  InetAddressIPv6
                     ACCESS  read-only
                     STATUS  mandatory
                     DESCRIPTION
                     "The IPv6 link local IP address for the ethernet interface.

                     NOTE: If extEthernetInterfaceIPv6Enabled is currently disabled, this
                     object has the value '0:0:0:0:0:0:0:0'."
                     ::= { extEthernetInterfaceIPv6LocalAddress 1 }

        extEthernetInterfaceIPv6StaticIPConfig  OBJECT IDENTIFIER ::= { extEthernetInterfaceIPv6Config 2 }

         extEthernetInterfaceIPv6StaticIPConfigEnabled  OBJECT-TYPE
                     SYNTAX  INTEGER { disabled(0), enabled(1) }
                     ACCESS  read-write
                     STATUS  mandatory
                     DESCRIPTION
                     "The IPv6 static IP address enabled or disabled state for the ethernet interface."
                     ::= { extEthernetInterfaceIPv6StaticIPConfig 1 }

         extEthernetInterfaceIPv6StaticIPAddress  OBJECT-TYPE
                     SYNTAX  InetAddressIPv6
                     ACCESS  read-write
                     STATUS  mandatory
                     DESCRIPTION
                     "The IPv6 static IP address for the ethernet interface.

                     NOTE: If extEthernetInterfaceIPv6Enabled is currently disabled, this
                     object has the value '0:0:0:0:0:0:0:0'."
                     ::= { extEthernetInterfaceIPv6StaticIPConfig 2 }

         extEthernetInterfaceIPv6StaticIPAddressPrefixLen  OBJECT-TYPE
                     SYNTAX  INTEGER (1..128)
                     ACCESS  read-write
                     STATUS  mandatory
                     DESCRIPTION
                     "The IPv6 static IP address prefix length for the ethernet interface.

                     NOTE: If extEthernetInterfaceIPv6Enabled is currently disabled, this
                     object has the value 0."
                     ::= { extEthernetInterfaceIPv6StaticIPConfig 3 }

         extEthernetInterfaceIPv6StaticIPDefaultRoute  OBJECT-TYPE
                     SYNTAX  InetAddressIPv6
                     ACCESS  read-write
                     STATUS  mandatory
                     DESCRIPTION
                     "The IPv6 static IP address default route for the ethernet interface.

                     NOTE: If extEthernetInterfaceIPv6Enabled is currently disabled, this
                     object has the value '0:0:0:0:0:0:0:0'."
                     ::= { extEthernetInterfaceIPv6StaticIPConfig 4 }

         extEthernetInterfaceIPv6LinkFloatingAddress  OBJECT-TYPE
                      SYNTAX  InetAddressIPv6
                      ACCESS  read-write
                      STATUS  mandatory
                      DESCRIPTION
                      "The IPv6 floating IP address for the external ethernet interface.
 
                      NOTE: If extEthernetInterfaceIPv6Enabled is currently disabled or the 
                            floating address is not configured, this object will return 
                            noSuchName."
                      ::= { extEthernetInterfaceIPv6StaticIPConfig 5 }

        extEthernetInterfaceIPv6AutoIPConfig  OBJECT IDENTIFIER ::= { extEthernetInterfaceIPv6Config 3 }

         extEthernetInterfaceIPv6AutoIPConfigEnabled  OBJECT-TYPE
                     SYNTAX  INTEGER {
                       disabled(0),
                       enabled(1)
                     }
                     ACCESS  read-write
                     STATUS  mandatory
                     DESCRIPTION
                     "The IPv6 automatic IP configuration enabled or disabled state for the ethernet interface.

                     NOTE: extEthernetInterfaceIPv6AutoIPConfigEnabled is the logical OR of extEthernetInterfaceDHCPv6Enabled
                     and extEthernetInterfaceIPv6StatelessAutoConfigEnabled settings.
                     NOTE: Enabling/Disabling extEthernetInterfaceIPv6AutoIPConfigEnabled will cause both
                     extEthernetInterfaceDHCPv6Enabled and extEthernetInterfaceIPv6StatelessAutoConfigEnabled to be enabled/disabled.
                     NOTE: extEthernetInterfaceIPv6StaticIPConfigEnabled and extEthernetInterfaceIPv6AutoIPConfigEnabled
                     cannot be disabled at the same time."
                     ::= { extEthernetInterfaceIPv6AutoIPConfig 1 }

         extEthernetInterfaceDHCPv6Config  OBJECT IDENTIFIER ::= { extEthernetInterfaceIPv6AutoIPConfig 2 }

          extEthernetInterfaceDHCPv6Enabled  OBJECT-TYPE
                     SYNTAX  INTEGER {
                       disabled(0),
                       enabled(1)
                     }
                     ACCESS  read-write
                     STATUS  mandatory
                     DESCRIPTION
                     "The DHCPv6 enabled or disabled state for the ethernet interface.

                     NOTE: If extEthernetInterfaceIPv6StatelessAutoConfigEnabled is currently disabled, Disabling
                     extEthernetInterfaceDHCPv6Enabled will cause extEthernetInterfaceIPv6AutoIPConfigEnabled to be disabled.
                     NOTE: If extEthernetInterfaceIPv6StaticIPConfigEnabled and
                     extEthernetInterfaceIPv6StatelessAutoConfigEnabled are currently disabled, Disabling
                     extEthernetInterfaceDHCPv6Enabled will not be allowed."
                     ::= { extEthernetInterfaceDHCPv6Config 1 }

           extEthernetInterfaceDHCPv6IPAddress  OBJECT-TYPE
                      SYNTAX  InetAddressIPv6
                      ACCESS  read-only
                      STATUS  mandatory
                      DESCRIPTION
                      "The IPv6 address for the ethernet interface, assigned by DHCPv6 server.

                      NOTE: If extEthernetInterfaceIPv6Enabled or extEthernetInterfaceDHCPv6Enabled
                      is disabled or if DHCPv6 server is not available, this object has the value
                      '0:0:0:0:0:0:0:0'."
                      ::= { extEthernetInterfaceDHCPv6Config 2 }

           extEthernetInterfaceDHCPv6DomainName  OBJECT-TYPE
                       SYNTAX  OCTET STRING (SIZE(0..64))
                       ACCESS  read-only
                       STATUS  mandatory
                       DESCRIPTION
                       "The 64 byte Domain Name for the ethernet interface,
                       assigned by the DHCPv6 server.

                       NOTE: If extEthernetInterfaceIPv6Enabled or extEthernetInterfaceDHCPv6Enabled
                       is disabled or if DHCPv6 server is not available, this object has the
                       value '(Not available)'."
                       ::= { extEthernetInterfaceDHCPv6Config 4 }

           extEthernetInterfaceDHCPv6PrimaryDNSServer  OBJECT-TYPE
                       SYNTAX  InetAddressIPv6
                       ACCESS  read-only
                       STATUS  mandatory
                       DESCRIPTION
                       "The primary DNS server, assigned by the DHCPv6 server.

                       NOTE: If extEthernetInterfaceIPv6Enabled or extEthernetInterfaceDHCPv6Enabled
                       is disabled or if DHCPv6 server is not available, this object has the
                       value '0:0:0:0:0:0:0:0'."
                       ::= { extEthernetInterfaceDHCPv6Config 5 }

           extEthernetInterfaceDHCPv6SecondaryDNSServer  OBJECT-TYPE
                       SYNTAX  InetAddressIPv6
                       ACCESS  read-only
                       STATUS  mandatory
                       DESCRIPTION
                       "The secondary DNS server, assigned by the DHCPv6 server.

                       NOTE: If extEthernetInterfaceIPv6Enabled or extEthernetInterfaceDHCPv6Enabled
                       is disabled or if DHCPv6 server is not available, this object has the
                       value '0:0:0:0:0:0:0:0'."
                       ::= { extEthernetInterfaceDHCPv6Config 6 }

           extEthernetInterfaceDHCPv6TertiaryDNSServer  OBJECT-TYPE
                       SYNTAX  InetAddressIPv6
                       ACCESS  read-only
                       STATUS  mandatory
                       DESCRIPTION
                       "The tertiary DNS server, assigned by the DHCPv6 server.

                       NOTE: If extEthernetInterfaceIPv6Enabled or extEthernetInterfaceDHCPv6Enabled
                       is disabled or if DHCPv6 server is not available, this object has the
                       value '0:0:0:0:0:0:0:0'."
                       ::= { extEthernetInterfaceDHCPv6Config 7 }

           extEthernetInterfaceDHCPv6Server  OBJECT-TYPE
                   SYNTAX  InetAddressIPv6
                   ACCESS  read-only
                   STATUS  mandatory
                   DESCRIPTION
                   "The DHCPv6 server IPv6 address used to acquire the DHCP settings.

                   NOTE: If extEthernetInterfaceIPv6Enabled or extEthernetInterfaceDHCPv6Enabled
                   is disabled or if DHCPv6 server is not available, this object has the
                   value '0:0:0:0:0:0:0:0'."
                   ::= { extEthernetInterfaceDHCPv6Config 8 }

         extEthernetInterfaceIPv6StatelessAutoConfig  OBJECT IDENTIFIER ::= { extEthernetInterfaceIPv6AutoIPConfig 3 }

          extEthernetInterfaceIPv6StatelessAutoConfigEnabled  OBJECT-TYPE
                     SYNTAX  INTEGER { disabled(0), enabled(1) }
                     ACCESS  read-write
                     STATUS  mandatory
                     DESCRIPTION
                     "The IPv6 stateless auto-configuration enabled or disabled state for the ethernet interface.

                     NOTE: If extEthernetfInterfaceDHCPv6Enabled is currently disabled, Disabling
                     extEthernetInterfaceIPv6StatelessAutoConfigEnabled will cause extEthernetInterfaceIPv6AutoIPConfigEnabled
                     to be disabled."
                     ::= { extEthernetInterfaceIPv6StatelessAutoConfig 1 }

       extEthernetInterfaceStatelessAutoConfigAddressesTable  OBJECT-TYPE
                    SYNTAX  SEQUENCE OF ExtEthernetInterfaceStatelessAutoConfigAddressesEntry
                    ACCESS  not-accessible
                    STATUS  mandatory
                    DESCRIPTION
                    "Table of stateless Auto-Config addresses entries"
                    ::= {  extEthernetInterfaceIPv6StatelessAutoConfig 2 }

       extEthernetInterfaceStatelessAutoConfigAddressesEntry  OBJECT-TYPE
                    SYNTAX  ExtEthernetInterfaceStatelessAutoConfigAddressesEntry
                    ACCESS  not-accessible
                    STATUS  mandatory
                    DESCRIPTION
                    "Stateless Auto-Config address entries"
                    INDEX { extEthernetInterfaceStatelessAutoConfigAddressesIndex }
                    ::= { extEthernetInterfaceStatelessAutoConfigAddressesTable 1 }

       ExtEthernetInterfaceStatelessAutoConfigAddressesEntry ::= SEQUENCE {
                   extEthernetInterfaceStatelessAutoConfigAddressesIndex INTEGER,
                   extEthernetInterfaceStatelessAutoConfigAddresses InetAddressIPv6,
                   extEthernetInterfaceStatelessAutoConfigAddressesPrefixLen INTEGER
                   }

       extEthernetInterfaceStatelessAutoConfigAddressesIndex   OBJECT-TYPE
                    SYNTAX  INTEGER
                    ACCESS  read-only
                    STATUS  mandatory
                    DESCRIPTION
                    "Index for stateless Auto-Config addresses.

                    NOTE: If extEthernetInterfaceIPv6StatelessAutoConfigEnabled or
                    extEthernetInterfaceIPv6Enabled is currently disabled, this
                    object will show nothing."
                    ::= { extEthernetInterfaceStatelessAutoConfigAddressesEntry 1 }

       extEthernetInterfaceStatelessAutoConfigAddresses   OBJECT-TYPE
                    SYNTAX   InetAddressIPv6
                    ACCESS  read-only
                    STATUS  mandatory
                    DESCRIPTION
                    "The stateless Auto-Configuration IPv6 address.

                    NOTE: If extEthernetInterfaceIPv6StatelessAutoConfigEnabled or
                    extEthernetInterfaceIPv6Enabled is currently disabled, this
                    object will show nothing."
                    ::= { extEthernetInterfaceStatelessAutoConfigAddressesEntry 2 }

       extEthernetInterfaceStatelessAutoConfigAddressesPrefixLen   OBJECT-TYPE
                    SYNTAX  INTEGER (1..128)
                    ACCESS  read-only
                    STATUS  mandatory
                    DESCRIPTION
                    "The stateless Auto-Configration address prefix length.

                    NOTE: If extEthernetInterfaceIPv6StatelessAutoConfigEnabled or
                    extEthernetInterfaceIPv6Enabled is currently disabled, this
                    object will show nothing."
                    ::= { extEthernetInterfaceStatelessAutoConfigAddressesEntry 3 }

       standbyExtEthernetInterfaceIPv6  OBJECT IDENTIFIER ::= { networkInterfaces 5 }

         standbyEthernetInterfaceIPv6LocalAddress  OBJECT IDENTIFIER ::= { standbyExtEthernetInterfaceIPv6 1 }

         standbyEthernetInterfaceIPv6LinkLocalAddress  OBJECT-TYPE
                     SYNTAX  InetAddressIPv6
                     ACCESS  read-only
                     STATUS  mandatory
                     DESCRIPTION
                     "The IPv6 link local IP address for the standby MM."
                     ::= { standbyEthernetInterfaceIPv6LocalAddress 1 }

         standbyEthernetInterfaceIPv6StaticIPConfig  OBJECT IDENTIFIER ::= { standbyExtEthernetInterfaceIPv6 2 }

         standbyEthernetInterfaceIPv6StaticIPConfigEnabled  OBJECT-TYPE
                     SYNTAX  INTEGER {
                       disabled(0),
                       enabled(1)
                     }
                     ACCESS  read-only
                     STATUS  mandatory
                     DESCRIPTION
                     "The IPv6 static IP address state for the MM.

                      NOTE: This value may be altered through the
                      extEthernetInterfaceIPv6StaticIPConfigEnabled object."
                     ::= { standbyEthernetInterfaceIPv6StaticIPConfig 1 }

         standbyEthernetInterfaceIPv6StaticIPAddress  OBJECT-TYPE
                     SYNTAX  InetAddressIPv6
                     ACCESS  read-write
                     STATUS  mandatory
                     DESCRIPTION
                     "The IPv6 static IP address for the standby MM

                     NOTE: If extEthernetInterfaceIPv6Enabled is currently disabled, this
                     object has the value '0:0:0:0:0:0:0:0'."
                     ::= { standbyEthernetInterfaceIPv6StaticIPConfig 2 }

         standbyEthernetInterfaceIPv6StaticIPAddressPrefixLen  OBJECT-TYPE
                     SYNTAX  INTEGER (1..128)
                     ACCESS  read-only
                     STATUS  mandatory
                     DESCRIPTION
                     "The IPv6 static IP address prefix length for the standyby MM.

                     NOTE: This value may be altered through the
                     extEthernetInterfaceIPv6StaticIPAddressPrefixLen object."
                     ::= { standbyEthernetInterfaceIPv6StaticIPConfig 3 }

         standbyEthernetInterfaceIPv6StaticIPDefaultRoute  OBJECT-TYPE
                     SYNTAX  InetAddressIPv6
                     ACCESS  read-only
                     STATUS  mandatory
                     DESCRIPTION
                     "The IPv6 static IP address default route for the standby MM.

                     NOTE: This value may be altered through the
                     extEthernetInterfaceIPv6StaticIPDefaultRoute object."
                     ::= { standbyEthernetInterfaceIPv6StaticIPConfig 4 }

         standbyEthernetInterfaceDHCPv6Config  OBJECT IDENTIFIER ::= {  standbyExtEthernetInterfaceIPv6 3 }

         standbyEthernetInterfaceDHCPv6Enabled  OBJECT-TYPE
                     SYNTAX  INTEGER {
                       disabled(0),
                       enabled(1)
                     }
                     ACCESS  read-only
                     STATUS  mandatory
                     DESCRIPTION
                     "The DHCPv6 enabled or disabled state for the standby MM.

                     NOTE: This field may be altered through the
                     extEthernetInterfaceDHCPv6Enabled object."
                     ::= { standbyEthernetInterfaceDHCPv6Config 1 }

           standbyEthernetInterfaceDHCPv6IPAddress  OBJECT-TYPE
                      SYNTAX  InetAddressIPv6
                      ACCESS  read-only
                      STATUS  mandatory
                      DESCRIPTION
                      "The IPv6 address for the standby MM assigned by DHCPv6 server."
                      ::= { standbyEthernetInterfaceDHCPv6Config 2 }

           standbyEthernetInterfaceDHCPv6DomainName  OBJECT-TYPE
                       SYNTAX  OCTET STRING (SIZE(0..64))
                       ACCESS  read-only
                       STATUS  mandatory
                       DESCRIPTION
                       "The 64 byte Domain Name for the standby MM
                       assigned by the DHCPv6 server."
                       ::= { standbyEthernetInterfaceDHCPv6Config 4 }

         standbyEthernetInterfaceStatelessAutoConfigAddressesTable  OBJECT-TYPE
                    SYNTAX  SEQUENCE OF StandbyEthernetInterfaceStatelessAutoConfigAddressesEntry
                    ACCESS  not-accessible
                    STATUS  mandatory
                    DESCRIPTION
                    "Table of stateless Auto-Config addresses entries.

                    NOTE: If extEthernetInterfaceIPv6StatelessAutoConfigEnabled or
                    extEthernetInterfaceIPv6Enabled is currently disabled, this
                    table will show nothing."
                    ::= {  standbyExtEthernetInterfaceIPv6 4 }

         standbyEthernetInterfaceStatelessAutoConfigAddressesEntry  OBJECT-TYPE
                    SYNTAX  StandbyEthernetInterfaceStatelessAutoConfigAddressesEntry
                    ACCESS  not-accessible
                    STATUS  mandatory
                    DESCRIPTION
                    "Stateless Auto-Config address entries"
                    INDEX { standbyEthernetInterfaceStatelessAutoConfigAddressesIndex }
                    ::= { standbyEthernetInterfaceStatelessAutoConfigAddressesTable 1 }

         StandbyEthernetInterfaceStatelessAutoConfigAddressesEntry ::= SEQUENCE {
                   standbyEthernetInterfaceStatelessAutoConfigAddressesIndex INTEGER,
                   standbyEthernetInterfaceStatelessAutoConfigAddresses InetAddressIPv6,
                   standbyEthernetInterfaceStatelessAutoConfigAddressesPrefixLen INTEGER
                   }

         standbyEthernetInterfaceStatelessAutoConfigAddressesIndex   OBJECT-TYPE
                    SYNTAX  INTEGER
                    ACCESS  read-only
                    STATUS  mandatory
                    DESCRIPTION
                    "Index for stateless Auto-Config addresses."
                    ::= { standbyEthernetInterfaceStatelessAutoConfigAddressesEntry 1 }

         standbyEthernetInterfaceStatelessAutoConfigAddresses   OBJECT-TYPE
                    SYNTAX   InetAddressIPv6
                    ACCESS  read-only
                    STATUS  mandatory
                    DESCRIPTION
                    "The stateless Auto-Configuration IPv6 address."
                    ::= { standbyEthernetInterfaceStatelessAutoConfigAddressesEntry 2 }

         standbyEthernetInterfaceStatelessAutoConfigAddressesPrefixLen   OBJECT-TYPE
                    SYNTAX  INTEGER (1..128)
                    ACCESS  read-only
                    STATUS  mandatory
                    DESCRIPTION
                    "The stateless Auto-Configration address prefix length."
                    ::= { standbyEthernetInterfaceStatelessAutoConfigAddressesEntry 3 }


       ddnsStatus   OBJECT-TYPE
                    SYNTAX  INTEGER { disabled(0), enabled(1) }
                    ACCESS  read-write
                    STATUS  mandatory
                    DESCRIPTION
                    "Dynamic DNS provides the capability for a networked device
                     to notify a domain name server to change, in real time, the
                     active DNS configuration of its configured hostnames, addresses
                     or other information stored in DNS. With Dynamic DNS, host
                     computers gain the capability to notify their respective DNS
                     server of the IP address they have received from a DHCP server
                     or through self-configuration."
                     ::= { networkInterfaces 10 }

       hostName      OBJECT-TYPE
                     SYNTAX  OCTET STRING (SIZE(0..64))
                     ACCESS  read-write
                     STATUS  mandatory
                     DESCRIPTION
                     "Contains the DNS host name for this system. This object
                     provides the exact same function as extEthernetInterfaceHostName"
                     ::= { networkInterfaces 11 }
       standbyHostName  OBJECT-TYPE
                     SYNTAX  OCTET STRING (SIZE(0..64))
                     ACCESS  read-write
                     STATUS  mandatory
                     DESCRIPTION
                     "Contains the DNS host name for the standby. This object
                     provides the exact same function as standbyExtEthernetInterfaceHostName
                     and is only applicable to systems with a standby MM."
                     ::= { networkInterfaces 12 }

       domainName    OBJECT-TYPE
                     SYNTAX  OCTET STRING
                     ACCESS  read-write
                     STATUS  mandatory
                     DESCRIPTION
                     "The user assigned DNS domain name."
                     ::= { networkInterfaces 13 }

       standbyDomainName    OBJECT-TYPE
                     SYNTAX  OCTET STRING
                     ACCESS  read-write
                     STATUS  mandatory
                     DESCRIPTION
                     "The user assigned DNS domain name of the standby. This is only
                     applicable to systems with a standby MM."
                     ::= { networkInterfaces 14 }

       activateNetworkUpdates    OBJECT-TYPE
                     SYNTAX INTEGER {
			noPendingUpdates(0),
			pendingUpdates(1)
                     }
                     ACCESS read-write
                     STATUS mandatory
		     DESCRIPTION
                     "When read, the return value indicates if there are any pending network
                     updates ready to be applied.  Writing any value will apply any pending
                     network updates immediately."
                     ::= { networkInterfaces 16 }

       -- ********************************************************************************
       -- VLAN Configuration
       -- ********************************************************************************
       vlanConfigure  OBJECT IDENTIFIER ::= { networkInterfaces 20 }

       vlanGlobalState  OBJECT-TYPE
                     SYNTAX  INTEGER { disable(0), enable(1) }
                     ACCESS  read-write
                     STATUS  mandatory
                     DESCRIPTION
                     "This object disables or enables the VLAN feature.  The
                     configuration objects for the VLAN are in the
                     vlanCMMTable.

                     The default setting for this object is disable(0).

                     IMPORTANT NOTE:  Any change to this object will revert
                     back to its previous value if the change is not
                     committed by setting the object vlanCommitState to
                     executeCommit(3) within the number of minutes indicated
                     in the object vlanCommitTimeout."
                     ::= { vlanConfigure 1 }

       vlanCommitTimeout  OBJECT-TYPE
                     SYNTAX  INTEGER (1..255)
                     ACCESS  read-write
                     STATUS  mandatory
                     DESCRIPTION
                     "This object is the number of minutes from the last
                     VLAN-related object change until any non-committed changes
                     will revert back to their previous settings.

                     This means if a user makes a change that disrupts TCP/IP
                     access to the CMM, the change will revert back to its
                     previous setting after the number of minutes in this
                     object.  This allows the user to access the CMM again
                     if access is lost through an unintended VLAN setting.

                     Once the changes are committed using the object,
                     vlanCommitState, setting it to executeCommit(3), the
                     changes will be saved in non-volatile memory.

                     The amount of time before uncommitted changes revert back
                     to their previous settings starts from the last change made
                     to any VLAN-related object.  If no other change is made,
                     the user has this number of minutes (the number in this
                     object) to commit the changes with vlanCommitState before
                     the changes will revert back.

                     The default setting for this object is 2 minutes.

                     IMPORTANT NOTE:  Any change to this object will revert
                     back to its previous value if the change is not
                     committed by setting the object vlanCommitState to
                     executeCommit(3) within the number of minutes indicated
                     in the object vlanCommitTimeout."
                     ::= { vlanConfigure 2 }

       vlanCommitState  OBJECT-TYPE
                     SYNTAX  INTEGER { noChangesPending(1), commitNeeded(2), executeCommit(3) }
                     ACCESS  read-write
                     STATUS  mandatory
                     DESCRIPTION
                     "This object gives the status of whether there are
                     VLAN-related changes pending that need to be committed,
                     and allows a user to commit (save) any VLAN changes.

                     If changes are pending, reading this object will give
                     a value of commitNeeded(2).  If no changes are pending,
                     this object will have the value of noChangesPending(1).

                     To save any VLAN-related changes so they do not revert
                     back to previous settings, set this object to
                     executeCommit(3) whenever this object has a value of
                     commitNeeded(2)."
                     ::= { vlanConfigure 3 }

      -- ********************************************************************************
      -- VLAN CMM Table Configuration
      -- ********************************************************************************
      vlanCMMTable OBJECT-TYPE
                     SYNTAX  SEQUENCE OF VlanCMMEntry
                     ACCESS  not-accessible
                     STATUS  mandatory
                     DESCRIPTION
                     "This table contains the VLAN configuration objects.
                     The default entry has an vlanCMMIndex equal to 1.
                     The objects for this default entry are configurable.

                     An additional VLAN entry may be added by setting the
                     object, vlanCMMEntryStatus, at vlanCMMIndex=2 to the value
                     of createRequest(2) and also setting the object,
                     vlanCMMVlanId, at vlanCMMIndex=2 to a valid, unique
                     value.

                     IMPORTANT NOTE:  Any changes to the object of this table
                     will revert back to their previous settings if the
                     changes are not committed by setting the object
                     vlanCommitState to executeCommit(3) within the number of
                     minutes indicated in the object vlanCommitTimeout."
                     ::= { vlanConfigure 20 }

      vlanCMMEntry OBJECT-TYPE
                     SYNTAX VlanCMMEntry
                     ACCESS  not-accessible
                     STATUS  mandatory
                     DESCRIPTION
                     "VLAN entries."
                     INDEX { vlanCMMIndex }
                     ::= { vlanCMMTable 1 }


      VlanCMMEntry ::=  SEQUENCE {
                     vlanCMMIndex INTEGER,
                     vlanCMMVlanId INTEGER,
                     vlanCMMName OCTET STRING,
                     vlanCMMEntryStatus EntryStatus,
                     vlanCMMState INTEGER,
                     vlanCMMSOLAccess INTEGER,
                     vlanCMMTagging INTEGER,
                     vlanCMMIPv4Address IpAddress,
                     vlanCMMIPv4Gateway IpAddress,
                     vlanCMMIPv4Mask IpAddress,
                     vlanCMMIPv4SubnetRoute1 IpAddress,
                     vlanCMMIPv4SubnetRouteMask1 IpAddress,
                     vlanCMMIPv4SubnetRoute2 IpAddress,
                     vlanCMMIPv4SubnetRouteMask2 IpAddress,
                     vlanCMMIPv4SubnetRoute3 IpAddress,
                     vlanCMMIPv4SubnetRouteMask3 IpAddress,
                     vlanCMMIPv6Address InetAddressIPv6,
                     vlanCMMIPv6AddressPrefixLen INTEGER,
                     vlanCMMIPv6Gateway InetAddressIPv6,
                     vlanCMMIPv6SubnetRoute1 InetAddressIPv6,
                     vlanCMMIPv6SubnetRoutePrefixLen1 INTEGER,
                     vlanCMMIPv6SubnetRoute2 InetAddressIPv6,
                     vlanCMMIPv6SubnetRoutePrefixLen2 INTEGER,
                     vlanCMMIPv6SubnetRoute3 InetAddressIPv6,
                     vlanCMMIPv6SubnetRoutePrefixLen3 INTEGER
                     }

      vlanCMMIndex  OBJECT-TYPE
                     SYNTAX  INTEGER (1..2)
                     ACCESS  read-only
                     STATUS  mandatory
                     DESCRIPTION
                     "Index for VLAN entry.  If vlanCMMIndex is equal to 1,
                     it is the Default VLAN entry and cannot be deleted."
                     ::= { vlanCMMEntry 1 }

      vlanCMMVlanId  OBJECT-TYPE
                     SYNTAX  INTEGER (1..4094)
                     ACCESS  read-write
                     STATUS  mandatory
                     DESCRIPTION
                     "Valid VLAN ID.  Allowed values are 5..4094.  If the entry
                     is not valid, this object will have the value of 0.

                     If this entry has the vlanCMMIndex value of 1 (default
                     VLAN entry), then setting this object will take effect
                     immediately.  For other entries, when this object is set,
                     this entry must have the object, vlanCMMState set to
                     enable(1) or restart(2) for this change to take effect."
                     ::= { vlanCMMEntry 2 }

      vlanCMMName  OBJECT-TYPE
                     SYNTAX  OCTET STRING (SIZE(0..31))
                     ACCESS  read-write
                     STATUS  mandatory
                     DESCRIPTION
                     "This object allows the user to configure a text string
                     name for this VLAN entry.  This entry name is only used
                     as a label for this entry."
                     ::= { vlanCMMEntry 3 }

      vlanCMMEntryStatus  OBJECT-TYPE
                     SYNTAX  EntryStatus
                     ACCESS  read-write
                     STATUS  mandatory
                     DESCRIPTION
                     "This object manages the creation and deletion of this
                     entry.
                     The steps recommended to add a new VLAN entry are:
                         1. Create a new entry in this table
                            vlanCMMEntryStatus = createRequest
                         2. Set vlanCMMVlanId as required.
                            Then the entry will be valid.

                     valid(1)         - Indicates that this entry is available
                                        for use.

                     createRequest(2) - A new entry will be created in this
                                        table and will transition to the
                                        vlanCMMEntryStatus value of
                                        underCreation(3).

                     underCreation(3) - Indicates that this entry exists in the
                                        agent but is unavailable for use. After
                                        completing the create operation, the
                                        agent will set this object to the value
                                        underCreation(3).

                     invalid(4)       - Deletes this entry.

                     The entry with the vlanCMMIndex value of 1 (default VLAN
                     entry) cannot be deleted."
                     ::= { vlanCMMEntry 4 }

      vlanCMMState  OBJECT-TYPE
                     SYNTAX  INTEGER {
                       disable(0),
                       enable(1),
                       restart(2)
                     }
                     ACCESS  read-write
                     STATUS  mandatory
                     DESCRIPTION
                     "This object indicates whether this VLAN entry is enabled
                     or disabled and allows the user to disable, enable or
                     restart this entry except for the exceptions noted below.

                     The entry with a vlanCMMIndex value of 1 (default VLAN
                     entry) will always have this object set to enable(1) and
                     cannot be set to any other value.  Other table entries do
                     not have this restriction.

                     Some other objects in this table may not take effect after
                     a change until either this object is: set to enable(1) if
                     this object currently has the value of disable(0), or set
                     to restart(2) if this object currently has the value of
                     enable(1). The other objects in this table that require
                     this object be set to enable(1) or restart(2) after a
                     change are noted in the description for those objects."
                     ::= { vlanCMMEntry 5 }

      vlanCMMSOLAccess  OBJECT-TYPE
                     SYNTAX  INTEGER { disable(0), enable(1) }
                     ACCESS  read-write
                     STATUS  mandatory
                     DESCRIPTION
                     "This object allows the user to set whether the VLAN
                     for this entry will have access to the Serial Over
                     LAN (SOL) interface.

                     Only one VLAN entry may have this object set to enable(1).

                     By default, the entry with the vlanCMMIndex value of 1
                     (default VLAN entry) will have this object set to
                     enable(1).

                     To set this object to enable(1) on another entry, this
                     object must first be set to disable(0) on any entry
                     that has this object set to enable(1)."
                     ::= { vlanCMMEntry 6 }

      vlanCMMTagging  OBJECT-TYPE
                     SYNTAX  INTEGER { disable(0), enable(1) }
                     ACCESS  read-write
                     STATUS  mandatory
                     DESCRIPTION
                     "This object allows the user to set whether VLAN tagging
                     is enabled for this VLAN entry.

                     This object is only configurable for the entry with the
                     vlanCMMIndex value of 1.

                     By default, the entry with the vlanCMMIndex value of 1
                     (default VLAN entry) will have this object set to
                     disable(0), all other entries will have this object set to
                     enable(1)."
                     ::= { vlanCMMEntry 8 }


      vlanCMMIPv4Address  OBJECT-TYPE
                     SYNTAX  IpAddress
                     ACCESS  read-write
                     STATUS  mandatory
                     DESCRIPTION
                     "This object sets the IPv4 address for this VLAN entry.

                     The entry with the vlanCMMIndex value of 1 (default VLAN
                     entry) will have this object set to the IP address of the
                     ethernet interface.  The IP address of the default VLAN
                     entry can only change by changing the IP address of the
                     ethernet interface.

                     For all other VLAN entries, this object may be set to any
                     IP address except the IP address of the ethernet
                     interface.

                     For a change of this object to take effect, the object,
                     vlanCMMState, must be set to enable(1) if the
                     vlanCMMState is currently disable(0), or set to
                     restart(2) if the vlanCMMState is currently enable(1)."
                     ::= { vlanCMMEntry 31 }

      vlanCMMIPv4Gateway  OBJECT-TYPE
                     SYNTAX  IpAddress
                     ACCESS  read-write
                     STATUS  mandatory
                     DESCRIPTION
                     "This object sets the IPv4 address for the IP gateway
                     for this VLAN entry.

                     The entry with the vlanCMMIndex value of 1 (default VLAN
                     entry) will have this object set to the IP gateway for the
                     ethernet interface.  The IP address of the default VLAN
                     entry can only change by changing the IP gateway of the
                     ethernet interface.

                     For all other VLAN entries, this object may be set to any
                     IP address except the IP address of the ethernet
                     interface.

                     For a change of this object to take effect, the object,
                     vlanCMMState, must be set to enable(1) if the
                     vlanCMMState is currently disable(0), or set to
                     restart(2) if the vlanCMMState is currently enable(1)."
                     ::= { vlanCMMEntry 32 }

      vlanCMMIPv4Mask  OBJECT-TYPE
                     SYNTAX  IpAddress
                     ACCESS  read-write
                     STATUS  mandatory
                     DESCRIPTION
                     "This object sets the IPv4 subnet mask for this VLAN
                     entry.

                     The entry with the vlanCMMIndex value of 1 (default VLAN
                     entry) will have this object set to the subnet mask of the
                     ethernet interface.  The subnet mask of the default VLAN
                     entry can only change by changing the subnet mask of the
                     ethernet interface.

                     For all other VLAN entries, this object may be set to any
                     valid subnet mask.

                     For a change of this object to take effect, the object,
                     vlanCMMState, must be set to enable(1) if the
                     vlanCMMState is currently disable(0), or set to
                     restart(2) if the vlanCMMState is currently enable(1)."
                     ::= { vlanCMMEntry 33 }

      vlanCMMIPv4SubnetRoute1  OBJECT-TYPE
                     SYNTAX  IpAddress
                     ACCESS  read-write
                     STATUS  mandatory
                     DESCRIPTION
                     "This object sets the IPv4 address of the subnet route 1
                     for this VLAN entry.

                     The entry with the vlanCMMIndex value of 1 (default VLAN
                     entry) will always have this object set to 0.0.0.0.

                     For all other VLAN entries, this object may be set to any
                     valid subnet route.

                     For a change of this object to take effect, the object,
                     vlanCMMState, must be set to enable(1) if the
                     vlanCMMState is currently disable(0), or set to
                     restart(2) if the vlanCMMState is currently enable(1)."
                     ::= { vlanCMMEntry 51 }

      vlanCMMIPv4SubnetRouteMask1  OBJECT-TYPE
                     SYNTAX  IpAddress
                     ACCESS  read-write
                     STATUS  mandatory
                     DESCRIPTION
                     "This object sets the IPv4 subnet route mask 1 for this
                     VLAN entry.

                     The entry with the vlanCMMIndex value of 1 (default VLAN
                     entry) will always have this object set to 0.0.0.0.

                     For all other VLAN entries, this object may be set to any
                     valid subnet mask.

                     For a change of this object to take effect, the object,
                     vlanCMMState, must be set to enable(1) if the
                     vlanCMMState is currently disable(0), or set to
                     restart(2) if the vlanCMMState is currently enable(1)."
                     ::= { vlanCMMEntry 52 }


      vlanCMMIPv4SubnetRoute2  OBJECT-TYPE
                     SYNTAX  IpAddress
                     ACCESS  read-write
                     STATUS  mandatory
                     DESCRIPTION
                     "This object sets the IPv4 address of the subnet route 2
                     for VLAN entry.

                     The entry with the vlanCMMIndex value of 1 (default VLAN
                     entry) will always have this object set to 0.0.0.0.

                     For all other VLAN entries, this object may be set to any
                     valid subnet route.

                     For a change of this object to take effect, the object,
                     vlanCMMState, must be set to enable(1) if the
                     vlanCMMState is currently disable(0), or set to
                     restart(2) if the vlanCMMState is currently enable(1)."
                     ::= { vlanCMMEntry 53 }

      vlanCMMIPv4SubnetRouteMask2  OBJECT-TYPE
                     SYNTAX  IpAddress
                     ACCESS  read-write
                     STATUS  mandatory
                     DESCRIPTION
                     "This object sets the IPv4 subnet route mask 2 for this
                     VLAN entry.

                     The entry with the vlanCMMIndex value of 1 (default VLAN
                     entry) will always have this object set to 0.0.0.0.

                     For all other VLAN entries, this object may be set to any
                     valid subnet mask.

                     For a change of this object to take effect, the object,
                     vlanCMMState, must be set to enable(1) if the
                     vlanCMMState is currently disable(0), or set to
                     restart(2) if the vlanCMMState is currently enable(1)."
                     ::= { vlanCMMEntry 54 }


      vlanCMMIPv4SubnetRoute3  OBJECT-TYPE
                     SYNTAX  IpAddress
                     ACCESS  read-write
                     STATUS  mandatory
                     DESCRIPTION
                     "This object sets the IPv4 address of the subnet route 3
                     for this VLAN entry.

                     The entry with the vlanCMMIndex value of 1 (default VLAN
                     entry) will always have this object set to 0.0.0.0.

                     For all other VLAN entries, this object may be set to any
                     valid subnet route.

                     For a change of this object to take effect, the object,
                     vlanCMMState, must be set to enable(1) if the
                     vlanCMMState is currently disable(0), or set to
                     restart(2) if the vlanCMMState is currently enable(1)."
                     ::= { vlanCMMEntry 55 }

      vlanCMMIPv4SubnetRouteMask3  OBJECT-TYPE
                     SYNTAX  IpAddress
                     ACCESS  read-write
                     STATUS  mandatory
                     DESCRIPTION
                     "This object sets the IPv4 subnet route mask 3 for this
                     VLAN entry.

                     The entry with the vlanCMMIndex value of 1 (default VLAN
                     entry) will always have this object set to 0.0.0.0.

                     For all other VLAN entries, this object may be set to any
                     valid subnet mask.

                     For a change of this object to take effect, the object,
                     vlanCMMState, must be set to enable(1) if the
                     vlanCMMState is currently disable(0), or set to
                     restart(2) if the vlanCMMState is currently enable(1)."
                     ::= { vlanCMMEntry 56 }

      vlanCMMIPv6Address OBJECT-TYPE
                     SYNTAX  InetAddressIPv6
                     ACCESS  read-write
                     STATUS  mandatory
                     DESCRIPTION
                     "This object sets the IPv6 address for this VLAN entry.

                     The entry with the vlanCMMIndex value of 1 (default VLAN
                     entry) will have this object set to the IP address of the
                     ethernet interface.  The IP address of the default VLAN
                     entry can only change by changing the IP address of the
                     ethernet interface.

                     For all other VLAN entries, this object may be set to any
                     IP address except the IP address of the ethernet
                     interface.

                     For a change of this object to take effect, the object,
                     vlanCMMState, must be set to enable(1) if the
                     vlanCMMState is currently disable(0), or set to
                     restart(2) if the vlanCMMState is currently enable(1)."
                     ::= { vlanCMMEntry 71 }

      vlanCMMIPv6AddressPrefixLen OBJECT-TYPE
                     SYNTAX  INTEGER (1..128)
                     ACCESS  read-write
                     STATUS  mandatory
                     DESCRIPTION
                     "This object sets the IPv6 address prefix length for this
                     VLAN entry.

                     The entry with the vlanCMMIndex value of 1 (default VLAN
                     entry) will have this object set to the IP address of the
                     ethernet interface.  The IP address of the default VLAN
                     entry can only change by changing the IP address of the
                     ethernet interface.

                     For all other VLAN entries, this object may be set to any
                     IP address except the IP address of the ethernet
                     interface.

                     For a change of this object to take effect, the object,
                     vlanCMMState, must be set to enable(1) if the
                     vlanCMMState is currently disable(0), or set to
                     restart(2) if the vlanCMMState is currently enable(1)."
                     ::= { vlanCMMEntry 72 }

      vlanCMMIPv6Gateway OBJECT-TYPE
                     SYNTAX  InetAddressIPv6
                     ACCESS  read-write
                     STATUS  mandatory
                     DESCRIPTION
                     "This object sets the IPv6 address for the IP gateway
                     for this VLAN entry.

                     The entry with the vlanCMMIndex value of 1 (default VLAN
                     entry) will have this object set to the IP gateway for the
                     ethernet interface.  The IP address of the default VLAN
                     entry can only change by changing the IP gateway of the
                     ethernet interface.

                     For all other VLAN entries, this object may be set to any
                     IP address except the IP address of the ethernet
                     interface.

                     For a change of this object to take effect, the object,
                     vlanCMMState, must be set to enable(1) if the
                     vlanCMMState is currently disable(0), or set to
                     restart(2) if the vlanCMMState is currently enable(1)."
                     ::= { vlanCMMEntry 73 }

      vlanCMMIPv6SubnetRoute1 OBJECT-TYPE
                     SYNTAX  InetAddressIPv6
                     ACCESS  read-write
                     STATUS  mandatory
                     DESCRIPTION
                     "This object sets the IPv6 address of the subnet route 1
                     for this VLAN entry.

                     The entry with the vlanCMMIndex value of 1 (default VLAN
                     entry) will always have this object set to 0.0.0.0.

                     For all other VLAN entries, this object may be set to any
                     valid subnet route.

                     For a change of this object to take effect, the object,
                     vlanCMMState, must be set to enable(1) if the
                     vlanCMMState is currently disable(0), or set to
                     restart(2) if the vlanCMMState is currently enable(1)."
                     ::= { vlanCMMEntry 91 }

      vlanCMMIPv6SubnetRoutePrefixLen1 OBJECT-TYPE
                     SYNTAX  INTEGER (1..128)
                     ACCESS  read-write
                     STATUS  mandatory
                     DESCRIPTION
                     "This object sets the IPv6 address prefix length of the
                     subnet route 1 for this VLAN entry.

                     The entry with the vlanCMMIndex value of 1 (default VLAN
                     entry) will have this object set to the IP address of the
                     ethernet interface.  The IP address of the default VLAN
                     entry can only change by changing the IP address of the
                     ethernet interface.

                     For all other VLAN entries, this object may be set to any
                     IP address except the IP address of the ethernet
                     interface.

                     For a change of this object to take effect, the object,
                     vlanCMMState, must be set to enable(1) if the
                     vlanCMMState is currently disable(0), or set to
                     restart(2) if the vlanCMMState is currently enable(1)."
                     ::= { vlanCMMEntry 92 }

      vlanCMMIPv6SubnetRoute2 OBJECT-TYPE
                     SYNTAX  InetAddressIPv6
                     ACCESS  read-write
                     STATUS  mandatory
                     DESCRIPTION
                     "This object sets the IPv6 address of the subnet route 2
                     for this VLAN entry.

                     The entry with the vlanCMMIndex value of 1 (default VLAN
                     entry) will always have this object set to 0.0.0.0.

                     For all other VLAN entries, this object may be set to any
                     valid subnet route.

                     For a change of this object to take effect, the object,
                     vlanCMMState, must be set to enable(1) if the
                     vlanCMMState is currently disable(0), or set to
                     restart(2) if the vlanCMMState is currently enable(1)."
                     ::= { vlanCMMEntry 93 }

      vlanCMMIPv6SubnetRoutePrefixLen2 OBJECT-TYPE
                     SYNTAX  INTEGER (1..128)
                     ACCESS  read-write
                     STATUS  mandatory
                     DESCRIPTION
                     "This object sets the IPv6 address prefix length of the
                     subnet route 2 for this VLAN entry.

                     The entry with the vlanCMMIndex value of 1 (default VLAN
                     entry) will have this object set to the IP address of the
                     ethernet interface.  The IP address of the default VLAN
                     entry can only change by changing the IP address of the
                     ethernet interface.

                     For all other VLAN entries, this object may be set to any
                     IP address except the IP address of the ethernet
                     interface.

                     For a change of this object to take effect, the object,
                     vlanCMMState, must be set to enable(1) if the
                     vlanCMMState is currently disable(0), or set to
                     restart(2) if the vlanCMMState is currently enable(1)."
                     ::= { vlanCMMEntry 94 }

      vlanCMMIPv6SubnetRoute3 OBJECT-TYPE
                     SYNTAX  InetAddressIPv6
                     ACCESS  read-write
                     STATUS  mandatory
                     DESCRIPTION
                     "This object sets the IPv6 address of the subnet route 3
                     for this VLAN entry.

                     The entry with the vlanCMMIndex value of 1 (default VLAN
                     entry) will always have this object set to 0.0.0.0.

                     For all other VLAN entries, this object may be set to any
                     valid subnet route.

                     For a change of this object to take effect, the object,
                     vlanCMMState, must be set to enable(1) if the
                     vlanCMMState is currently disable(0), or set to
                     restart(2) if the vlanCMMState is currently enable(1)."
                     ::= { vlanCMMEntry 95 }

      vlanCMMIPv6SubnetRoutePrefixLen3 OBJECT-TYPE
                     SYNTAX  INTEGER (1..128)
                     ACCESS  read-write
                     STATUS  mandatory
                     DESCRIPTION
                     "This object sets the IPv6 address prefix length of the
                     subnet route 3 for this VLAN entry.

                     The entry with the vlanCMMIndex value of 1 (default VLAN
                     entry) will have this object set to the IP address of the
                     ethernet interface.  The IP address of the default VLAN
                     entry can only change by changing the IP address of the
                     ethernet interface.

                     For all other VLAN entries, this object may be set to any
                     IP address except the IP address of the ethernet
                     interface.

                     For a change of this object to take effect, the object,
                     vlanCMMState, must be set to enable(1) if the
                     vlanCMMState is currently disable(0), or set to
                     restart(2) if the vlanCMMState is currently enable(1)."
                     ::= { vlanCMMEntry 96 }

      -- *************************************************************************
      -- vlanCMMTableCacheTimeout
      -- *************************************************************************
      vlanCMMTableCacheTimeout OBJECT-TYPE
                   SYNTAX  INTEGER
                   ACCESS  read-only
                   STATUS  mandatory
                   DESCRIPTION
                   "The timeout value (in seconds) of the cached data for the
                   table, vlanCMMTable.
                   This value is static (constant) and cannot be set."
                     ::= { vlanConfigure 21 }

       -- ********************************************************************************
       -- TCP/IP Protocol Configuration
       -- ********************************************************************************
       tcpProtocols  OBJECT IDENTIFIER ::= { networkConfiguration 3 }

        -- ********************************************************************************
        -- SNMP Agent Configuration
        -- ********************************************************************************
        snmpAgentConfig  OBJECT IDENTIFIER ::= { tcpProtocols 1 }


         snmpSystemContact     OBJECT-TYPE
                      SYNTAX  OCTET STRING (SIZE(0..48))
                      ACCESS  read-write
                      STATUS  mandatory
                      DESCRIPTION
                      "A NULL terminated 48 byte string that contains the
                      SNMP agent contact name."
                      ::= { snmpAgentConfig 1 }

         snmpSystemLocation     OBJECT-TYPE
                      SYNTAX  OCTET STRING (SIZE(0..48))
                      ACCESS  read-write
                      STATUS  mandatory
                      DESCRIPTION
                      "A NULL terminated 48 byte string that contains the
                      SNMP agent location name."
                      ::= { snmpAgentConfig 2 }

         snmpSystemAgentTrapsDisable  OBJECT-TYPE
                      SYNTAX  INTEGER {
                        trapsEnabled(0),
                        trapsDisabled(1)
                      }
                      ACCESS  read-write
                      STATUS  mandatory
                      DESCRIPTION
                      "Disable or enable SNMP traps."
                      ::= { snmpAgentConfig 3 }

         -- ********************************************************************************
         -- SNMP Agent Community Configuration
         -- ********************************************************************************
         snmpAgentCommunityConfig  OBJECT IDENTIFIER ::= { snmpAgentConfig 4 }

          -- ********************************************************************************
          -- SNMP Community Configuration table
          -- ********************************************************************************

          snmpCommunityTable  OBJECT-TYPE
                                SYNTAX  SEQUENCE OF SnmpCommunityEntry
                                ACCESS  not-accessible
                                STATUS  mandatory
                                DESCRIPTION
                                "Table of SNMP Community entries"
                                ::= {  snmpAgentCommunityConfig 1 }

          snmpCommunityEntry  OBJECT-TYPE
                                SYNTAX  SnmpCommunityEntry
                                ACCESS  not-accessible
                                STATUS  mandatory
                                DESCRIPTION
                                "SNMP community entries"
                                INDEX { snmpCommunityEntryIndex }
                                ::= { snmpCommunityTable 1 }

          SnmpCommunityEntry ::= SEQUENCE {
                       snmpCommunityEntryIndex INTEGER,
                       snmpCommunityEntryCommunityName OCTET STRING,
                       snmpCommunityEntryCommunityIpAddress1 OCTET STRING,
                       snmpCommunityEntryCommunityIpAddress2 OCTET STRING,
                       snmpCommunityEntryCommunityIpAddress3 OCTET STRING,
                       snmpCommunityEntryCommunityViewType INTEGER
                       }

          snmpCommunityEntryIndex   OBJECT-TYPE
                                    SYNTAX  INTEGER(0..255)
                                    ACCESS  read-only
                                    STATUS  mandatory
                                    DESCRIPTION
                                    "Index for SNMP Agent Community entry."
                                    ::= { snmpCommunityEntry 1 }

          snmpCommunityEntryCommunityName  OBJECT-TYPE
                                    SYNTAX  OCTET STRING (SIZE(0..15))
                                    ACCESS  read-write
                                    STATUS  mandatory
                                    DESCRIPTION
                                    "SNMP Community entry name."
                                    ::= { snmpCommunityEntry 2 }

          snmpCommunityEntryCommunityIpAddress1  OBJECT-TYPE
                                    SYNTAX  OCTET STRING (SIZE(0..63))
                                    ACCESS  read-write
                                    STATUS  mandatory
                                    DESCRIPTION
                                    "SNMP Community IP address or host name.
                                    Can either be a dotted decimal IP string (e.g. 9.37.44.2)
                                    or if DNS is enabled a host name. This field also allows two
                                    wildard values for read-Traps and write-Read-Traps communities:
                                      0.0.0.0 - allow any IPv4 address
                                      0::0    - allow any IPv6 address"
                                    ::= { snmpCommunityEntry 3 }

          snmpCommunityEntryCommunityIpAddress2  OBJECT-TYPE
                                    SYNTAX  OCTET STRING (SIZE(0..63))
                                    ACCESS  read-write
                                    STATUS  mandatory
                                    DESCRIPTION
                                    "SNMP Community IP address or host name.
                                    Can either be a dotted decimal IP string (e.g. 9.37.44.2)
                                    or if DNS is enabled a host name. This field also allows two
                                    wildard values for read-Traps and write-Read-Traps communities:
                                      0.0.0.0 - allow any IPv4 address
                                      0::0    - allow any IPv6 address"
                                    ::= { snmpCommunityEntry 4 }

          snmpCommunityEntryCommunityIpAddress3  OBJECT-TYPE
                                    SYNTAX  OCTET STRING (SIZE(0..63))
                                    ACCESS  read-write
                                    STATUS  mandatory
                                    DESCRIPTION
                                    "SNMP Community IP address or host name.
                                    Can either be a dotted decimal IP string (e.g. 9.37.44.2)
                                    or if DNS is enabled a host name. This field also allows two
                                    wildard values for read-Traps and write-Read-Traps communities:
                                      0.0.0.0 - allow any IPv4 address
                                      0::0    - allow any IPv6 address"
                                    ::= { snmpCommunityEntry 5 }

          snmpCommunityEntryCommunityViewType  OBJECT-TYPE
                                     SYNTAX  INTEGER {
                                     read-Traps(1),
                                     write-Read-Traps(2),
                                     traps-Only(3)
                                     }
                                     ACCESS  read-write
                                     STATUS  mandatory
                                     DESCRIPTION
                                     "Access Level of the SNMPv1 managers.  Note this parameter
                                     is set for each community.  Therefore all three managers
                                     in the same community have the same access level."
                                     ::= { snmpCommunityEntry 6 }

         snmpv1SystemAgentEnable  OBJECT-TYPE
                      SYNTAX  INTEGER {
                        disabled(0),
                        enabled(1)
                      }
                      ACCESS  read-write
                      STATUS  mandatory
                      DESCRIPTION
                      "Disable or enable the SNMPv1 agent.

                      NOTE: Restart the management module if this MIB object is changed
                      with respect to the value at system bootup time.  For example the
                      SNMPv1 agent was set to disabled at system bootup time and now
                      it is enabled.  Then restarting the remote supervisor is required.

                      Also note that when attempting to enable this agent,
                      the following are verified:
                      (1) Is there a valid system contact
                      (2) Is there a valid system name
                      (3) Is there at least one valid community name and for that
                      community name is there one valid IP address or hostname
                      (4) Are all defined community names unique

                      If this verification fails an error response will be returned
                      and the SNMPv1 agent will be left disabled."
                      ::= { snmpAgentConfig 5 }

         snmpv3SystemAgentEnable  OBJECT-TYPE
                      SYNTAX  INTEGER {
                        disabled(0),
                        enabled(1)
                      }
                      ACCESS  read-write
                      STATUS  mandatory
                      DESCRIPTION
                      "Disable or enable the SNMPv3 agent.

                      NOTE: Restart the management module if this MIB object is changed
                      with respect to the value at system bootup time.  For example the
                      SNMPv3 agent was set to disabled at system bootup time and now
                      it is enabled.  Then restarting the remote supervisor is required.

                      Also note that when attempting to enable this agent,
                      the following are verified:
                      (1) Is there a valid system contact?
                      (2) Is there a valid system name?

                      If this verification fails an error response will be returned
                      and the SNMPv3 agent will be left disabled."

                      ::= { snmpAgentConfig 6 }

         -- ********************************************************************************
         -- SNMP Agent User Profile Configuration
         -- ********************************************************************************

         snmpAgentUserProfileConfig  OBJECT IDENTIFIER ::= { snmpAgentConfig 9 }

          -- ********************************************************************************
          -- SNMP User Profile Configuration table
          -- ********************************************************************************

          snmpUserProfileTable  OBJECT-TYPE
                                SYNTAX  SEQUENCE OF SnmpUserProfileEntry
                                ACCESS  not-accessible
                                STATUS  mandatory
                                DESCRIPTION
                                "Table of SNMPv3 User Profile entries"
                                ::= {  snmpAgentUserProfileConfig 1 }

          snmpUserProfileEntry  OBJECT-TYPE
                                SYNTAX  SnmpUserProfileEntry
                                ACCESS  not-accessible
                                STATUS  mandatory
                                DESCRIPTION
                                "SNMP User Profile entries"
                                INDEX { snmpUserProfileEntryIndex }
                                ::= { snmpUserProfileTable 1 }

          SnmpUserProfileEntry ::= SEQUENCE {
                       snmpUserProfileEntryIndex INTEGER,
                       snmpUserProfileEntryContextName OCTET STRING,
                       snmpUserProfileEntryAuthProt INTEGER,
                       snmpUserProfileEntryPrivProt INTEGER,
                       snmpUserProfileEntryPrivPassword OCTET STRING,
                       snmpUserProfileEntryViewType INTEGER,
                       snmpUserProfileEntryIpAddress OCTET STRING,
                       snmpUserProfileEntryUserId OCTET STRING
                       }

          snmpUserProfileEntryIndex   OBJECT-TYPE
                                    SYNTAX  INTEGER(0..255)
                                    ACCESS  read-only
                                    STATUS  mandatory
                                    DESCRIPTION
                                    "Index for SNMPv3 Agent User Profile entry."
                                    ::= { snmpUserProfileEntry 1 }

          snmpUserProfileEntryContextName  OBJECT-TYPE
                                    SYNTAX  OCTET STRING (SIZE(0..31))
                                    ACCESS  read-write
                                    STATUS  mandatory
                                    DESCRIPTION
                                    "SNMPv3 User Profile entry - Context name
                                    for users to access MIB objects.  Note that context names can be duplicates
                                    and can be shared among users.  Empty context names are allowed.  The
                                    default context name is the empty string."
                                    ::= { snmpUserProfileEntry 3 }

          snmpUserProfileEntryAuthProt   OBJECT-TYPE
                                    SYNTAX  INTEGER {
                                    md5 (2),
                                    sha (3)
                                    }
                                    ACCESS  read-write
                                    STATUS  mandatory
                                    DESCRIPTION
                                    "SNMPv3 User Profile entry - Authentication Protocol
                                    supported by the user."
                                    ::= { snmpUserProfileEntry 4 }

            snmpUserProfileEntryPrivProt   OBJECT-TYPE
                                    SYNTAX  INTEGER {
                                    none (1),
                                    des (2),
                                    aes (4)
                                    }
                                    ACCESS  read-write
                                    STATUS  mandatory
                                    DESCRIPTION
                                    "SNMPv3 User Profile entry - Privacy Protocol
                                    supported by the user. The Privacy Password must be set
                                    and the Authentication Protocol must be md5 or sha
                                    before this field may be set to des or aes."
                                    ::= { snmpUserProfileEntry 6 }

           snmpUserProfileEntryPrivPassword  OBJECT-TYPE
                                    SYNTAX  OCTET STRING (SIZE(0..31))
                                    ACCESS  read-write
                                    STATUS  mandatory
                                    DESCRIPTION
                                    "SNMPv3 User Profile entry - Privacy password
                                    for the user.

                                    NOTE: Value returned for the GET command is
                                    meaningless for this MIB object for security reasons."
                                    ::= { snmpUserProfileEntry 7 }

            snmpUserProfileEntryViewType   OBJECT-TYPE
                                    SYNTAX  INTEGER {
                                    read-Traps(1),
                                    read-Write-Traps(2),
                                    traps-Only(3)
                                    }
                                    ACCESS  read-write
                                    STATUS  mandatory
                                    DESCRIPTION
                                    "SNMPv3 User Profile entry - Access level (Get, Set, and
                                    Traps) of the user. "
                                    ::= { snmpUserProfileEntry 8 }

           snmpUserProfileEntryIpAddress  OBJECT-TYPE
                                    SYNTAX  OCTET STRING (SIZE(0..63))
                                    ACCESS  read-write
                                    STATUS  mandatory
                                    DESCRIPTION
                                    "SNMPv3 User Profile entry - IP address or host name.
                                    Can either be a dotted decimal IP string (e.g. 9.37.44.2)
                                    or if DNS is enabled a host name."
                                    ::= { snmpUserProfileEntry 9 }

           snmpUserProfileEntryUserId  OBJECT-TYPE
                                    SYNTAX  OCTET STRING (SIZE(0..31))
                                    ACCESS  read-only
                                    STATUS  mandatory
                                    DESCRIPTION
                                    "The userid for the SNMPv3 Agent User Profile entry."
                                    ::= { snmpUserProfileEntry 10 }

        -- ********************************************************************************
        -- DNS Configuration
        -- ********************************************************************************
        dnsConfig  OBJECT IDENTIFIER ::= { tcpProtocols 2 }

         dnsEnabled   OBJECT-TYPE
                      SYNTAX  INTEGER {
                        dnsDisabled(0),
                        dnsEnabled(1)
                      }
                      ACCESS  read-write
                      STATUS  mandatory
                      DESCRIPTION
                      "Disable or enable the DNS agent.

                      NOTE: To alter any of the configuration settings for the DNS agent,
                      the following procedure should be used:
                      (1) This object should be set to 'disabled'
                      (2) Make the modifications to other settings
                      (3) This object should be set to 'enabled'

                      Also note that when attempting to enable this agent, it is verified
                      that there is at least one valid DNS server IP address.  If this
                      verification fails, an error response will be returned and the DNS
                      agent will be left disabled."
                      ::= { dnsConfig 1 }

         dnsServerIPAddress1   OBJECT-TYPE
                      SYNTAX  IpAddress
                      ACCESS  read-write
                      STATUS  mandatory
                      DESCRIPTION
                      "Contains the primary DNS server IP address."
                      ::= { dnsConfig 2 }

         dnsServerIPAddress2   OBJECT-TYPE
                      SYNTAX  IpAddress
                      ACCESS  read-write
                      STATUS  mandatory
                      DESCRIPTION
                      "Contains the secondary DNS server IP address."
                      ::= { dnsConfig 3 }

         dnsServerIPAddress3   OBJECT-TYPE
                      SYNTAX  IpAddress
                      ACCESS  read-write
                      STATUS  mandatory
                      DESCRIPTION
                      "Contains the tertiary DNS server IP address."
                      ::= { dnsConfig 4 }

         dnsServerIPv6Address1   OBJECT-TYPE
                      SYNTAX  InetAddressIPv6
                      ACCESS  read-write
                      STATUS  mandatory
                      DESCRIPTION
                      "Contains the primary IPv6 DNS server address."
                      ::= { dnsConfig 12 }

         dnsServerIPv6Address2   OBJECT-TYPE
                      SYNTAX  InetAddressIPv6
                      ACCESS  read-write
                      STATUS  mandatory
                      DESCRIPTION
                      "Contains the secondary IPv6 DNS server address."
                      ::= { dnsConfig 13 }

         dnsServerIPv6Address3   OBJECT-TYPE
                      SYNTAX  InetAddressIPv6
                      ACCESS  read-write
                      STATUS  mandatory
                      DESCRIPTION
                      "Contains the tertiary IPv6 DNS server address."
                      ::= { dnsConfig 14 }

         dnsPriority   OBJECT-TYPE
                      SYNTAX  INTEGER {
                        ipv6(1),
                        ipv4(2)
                      }
                      ACCESS  read-write
                      STATUS  mandatory
                      DESCRIPTION
                      "Tells the order host names are resolved. The options are
                      to either first resolve with an IPv4 DNS server or to first
                      resolve with an IPv6 DNS server."
                      ::= { dnsConfig 20 }

        -- ********************************************************************************
        -- SMTP Configuration
        -- ********************************************************************************
        smtpConfig  OBJECT IDENTIFIER ::= { tcpProtocols 3 }

         smtpServerNameOrIPAddress     OBJECT-TYPE
                      SYNTAX  OCTET STRING (SIZE(0..64))
                      ACCESS  read-write
                      STATUS  mandatory
                      DESCRIPTION
                      "A NULL terminated 64 byte string that contains the
                      SMTP server host name or IP address (a.b.c.d)."
                      ::= { smtpConfig 1 }

         attachmentsToEmailAlerts  OBJECT-TYPE
                      SYNTAX  INTEGER {
                        noAttachments(0),
                        attachServiceInformation(1)
                      }
                      ACCESS  read-write
                      STATUS  mandatory
                      DESCRIPTION
                      "Indicates if the service information should be attached to
                      an email alert."
                      ::= { smtpConfig 2 }
                      
         smtpEmailDomain     OBJECT-TYPE
                      SYNTAX  OCTET STRING (SIZE(0..64))
                      ACCESS  read-write
                      STATUS  mandatory
                      DESCRIPTION
                        "A NULL terminated string that contains the
                         SMTP email domain. If this field is empty, the MM IP 
                         address is used as the domain. However, some SMTP 
                         servers (e.g. - MS Exchange 2007) do not accept an IP address and
                         instead require a domain name. This object can be used to set that
                         email domain name."
                      ::= { smtpConfig 3 }

        tcpApplicationConfig  OBJECT IDENTIFIER ::= { tcpProtocols 4 }
         telnetInactivityTimeout  OBJECT-TYPE
                      SYNTAX  INTEGER
                      ACCESS  read-write
                      STATUS  mandatory
                      DESCRIPTION
                      "Default is 300 seconds. Value of zero is no timeout.
                      Max value is any positive 4 bytes value. Note that SSH also uses this
                      timeout value to wait before disconnecting inactive SSH connections."
                      ::= { tcpApplicationConfig 1 }

         commandModeInactivityTimeout  OBJECT-TYPE
                      SYNTAX  INTEGER
                      ACCESS  read-write
                      STATUS  mandatory
                      DESCRIPTION
                      "The amount of time in seconds before the (Secure)TCP Command Mode times out.
                      Default value of 0 means no timeout. Max value is any positive 4 byte value."
                      ::= { tcpApplicationConfig 2 }

          secureCommandModeEnable   OBJECT-TYPE
                      SYNTAX  INTEGER
                      ACCESS  read-write
                      STATUS  mandatory
                      DESCRIPTION
                      "Set Secure TCP Command Mode number of connections.
                      MM will provide a max of 20 connections for both Secure TCP Command Mode and TCP Command Mode.
                      A value of 0 means disabled.
                      If no valid server certificate is in place, Secure TCP Command Mode will not be allowed to set to enable."
                      ::= { tcpApplicationConfig 3 }

         commandModeEnable  OBJECT-TYPE
                      SYNTAX  INTEGER
                      ACCESS  read-write
                      STATUS  mandatory
                      DESCRIPTION
                      "Set TCP Command Mode number of connections.
                      MM will provide a max of 20 connections for both Secure TCP Command Mode and TCP Command Mode.
                      A value of 0 means disabled."
                      ::= { tcpApplicationConfig 4 }

         slpAddrType  OBJECT-TYPE
                      SYNTAX  INTEGER {
                        multicast(0),
                        broadcast(1)
                      }
                      ACCESS  read-write
                      STATUS  mandatory
                      DESCRIPTION
                      "Set SLP address type to 0 (multicast) or 1 (broadcast). Note that when
                      slpAddrType is set to broadcast value then the multicast address set in
                      slpMulticastAddr will be ignored."
                      ::= { tcpApplicationConfig 5 }

         slpEnable  OBJECT-TYPE
                      SYNTAX  INTEGER {
                        disabled(0),
                        enabled(1)
                      }
                      ACCESS  read-write
                      STATUS  mandatory
                      DESCRIPTION
                      "Disable/Enable Service Location Protocol.

                      NOTE: Change to Service Location Protocol will take
                      effect after the next restart of the MM."
                      ::= { tcpApplicationConfig 7}

         telnetEnable  OBJECT-TYPE
                      SYNTAX  INTEGER {
                        disabled(0),
                        enabled(1)
                      }
                      ACCESS  read-write
                      STATUS  mandatory
                      DESCRIPTION
                      "Disable/Enable telnet.
                      NOTE: Change to telnet enable/disable will take effect immediately."
                      ::= { tcpApplicationConfig 9 }

         sshEnable  OBJECT-TYPE
                      SYNTAX  INTEGER {
                        disabled(0),
                        enabled(1)
                      }
                      ACCESS  read-write
                      STATUS  mandatory
                      DESCRIPTION
                      "Disable/Enable SSH."
                      ::= { tcpApplicationConfig 10 }

         sslServerEnable  OBJECT-TYPE
                      SYNTAX  INTEGER {
                        disabled(0),
                        enabled(1)
                      }
                      ACCESS  read-write
                      STATUS  mandatory
                      DESCRIPTION
                      "Disable/Enable SSL Server."
                      ::= { tcpApplicationConfig 15 }

         sslClientEnable  OBJECT-TYPE
                      SYNTAX  INTEGER {
                        disabled(0),
                        enabled(1)
                      }
                      ACCESS  read-write
                      STATUS  mandatory
                      DESCRIPTION
                      "Disable/Enable SSL Client.  If no valid client or server certificate is in place,
                      SSL client will not be allowed to set to enable."
                      ::= { tcpApplicationConfig 16 }

         ftpEnable    OBJECT-TYPE
                      SYNTAX  INTEGER {
                        disabled(0),
                        enabled(1)
                      }
                      ACCESS  read-write
                      STATUS  mandatory
                      DESCRIPTION
                      "Disable/Enable FTP."
                      ::= { tcpApplicationConfig 17 }

        sftpEnable   OBJECT-TYPE
                      SYNTAX  INTEGER {
                        disabled(0),
                        enabled(1)
                      }
                      ACCESS  read-write
                      STATUS  mandatory
                      DESCRIPTION
                      "Disable/Enable SFTP."
                      ::= { tcpApplicationConfig 18 }



         tftpEnable   OBJECT-TYPE
                      SYNTAX  INTEGER {
                        disabled(0),
                        enabled(1)
                      }
                      ACCESS  read-write
                      STATUS  mandatory
                      DESCRIPTION
                      "Disable/Enable TFTP."
                      ::= { tcpApplicationConfig 19 }

         ftpTimeout   OBJECT-TYPE
                      SYNTAX  INTEGER
                      ACCESS  read-write
                      STATUS  mandatory
                      DESCRIPTION
                      "The amount of time before FTP times out.  Default is 300 seconds.
                      Value of zero is no timeout. Max value is any positive 4 byte value."
                      ::= { tcpApplicationConfig 23 }

         cimEnable    OBJECT-TYPE
                      SYNTAX  INTEGER {
                        disabled(0),
                        enabled(1)
                      }
                      ACCESS  read-write
                      STATUS  mandatory
                      DESCRIPTION
                      "Disable/Enable CIM (Common Information Model) interface.
                      NOTE: Change to CIM enable/disable will take effect immediately."
                      ::= { tcpApplicationConfig 50 }

        -- The SSH Server Configuration Group

        mmSshServerConfig OBJECT IDENTIFIER ::= { tcpApplicationConfig 27 }

         mmSshServerHostKeyTable OBJECT-TYPE
                        SYNTAX  SEQUENCE OF MmSshServerHostKeyEntry
                        ACCESS  not-accessible
                        STATUS  mandatory
                        DESCRIPTION
                        "A table that contains per public/private host key
                        pair information."
                        ::= { mmSshServerConfig 1 }

         mmSshServerHostKeyEntry OBJECT-TYPE
                        SYNTAX  MmSshServerHostKeyEntry
                        ACCESS  not-accessible
                        STATUS  mandatory
                        DESCRIPTION
                        "A list of information about a particular public/private
                        host key pair."
                        INDEX { mmSshServerHostKeyIndex }
                        ::= { mmSshServerHostKeyTable 1 }

         MmSshServerHostKeyEntry ::= SEQUENCE {
                        mmSshServerHostKeyIndex  INTEGER,
                        mmSshServerHostKeyType  INTEGER,
                        mmSshServerHostKeySize  INTEGER,
                        mmSshServerHostKeyFingerprint  OCTET STRING
                        }

         mmSshServerHostKeyIndex  OBJECT-TYPE
                        SYNTAX  INTEGER
                        ACCESS  read-only
                        STATUS  mandatory
                        DESCRIPTION
                        "The index of the public/private host key pair."
                        ::= { mmSshServerHostKeyEntry 1 }

         mmSshServerHostKeyType  OBJECT-TYPE
                        SYNTAX  INTEGER {
                            sshDss   (1),
                            sshRsa   (2)
                        }
                        ACCESS  read-only
                        STATUS  mandatory
                        DESCRIPTION
                        "The type of the public/private host key pair."
                        ::= { mmSshServerHostKeyEntry 2 }

         mmSshServerHostKeySize  OBJECT-TYPE
                        SYNTAX  INTEGER {
                             bits512   (1),
                             bits768   (2),
                             bits1024  (3),
                             bits2048  (4),
                             bits4096  (5)
                        }
                        ACCESS  read-only
                        STATUS  mandatory
                        DESCRIPTION
                        "The size of the public/private host key pair.

                        NOTE: The MM supports only the bits2048 value."
                        ::= { mmSshServerHostKeyEntry 3 }

         mmSshServerHostKeyFingerprint  OBJECT-TYPE
                        SYNTAX  OCTET STRING
                        ACCESS  read-only
                        STATUS  mandatory
                        DESCRIPTION
                        "The RSA fingerprint of the public part of the host key
                        pair.  This value can be used with the SSH client to
                        verify, on the initial connection, that the Secure Shell
                        server responding to the request is the server running
                        on the MM. "
                        ::= { mmSshServerHostKeyEntry 4 }

         mmSshServerHostKeyGenerate OBJECT-TYPE
                        SYNTAX  INTEGER {
                        execute(1)
                        }
                        ACCESS  read-write
                        STATUS  mandatory
                        DESCRIPTION
                        "Initiate the new Host Keys generation process for the
                        MM SSH Server.

                        NOTE: Value returned for the GET command is meaningless
                        for this MIB object."
                        ::= { mmSshServerConfig 2 }

         mmSshServerHostKeyGenerateProgress OBJECT-TYPE
                        SYNTAX  OCTET STRING
                        ACCESS  read-only
                        STATUS  mandatory
                        DESCRIPTION
                        "Indicate the progress of the key generation process."
                        ::= { mmSshServerConfig 3 }

        -- TCP Port Assignment
        tcpPortAssignmentCfg    OBJECT IDENTIFIER ::= { tcpProtocols 5 }

         tcpPortsRestoreDefault   OBJECT-TYPE
                      SYNTAX  INTEGER  {
                        execute(1)
                      }
                      ACCESS  read-write
                      STATUS  mandatory
                      DESCRIPTION
                      "Reset all ports to default value.
                         http: 80
                         https: 443
                         telnet: 23
                         ssh: 22
                         SNMP agent: 161
                         SNMP trap: 162
                         TCP Command Mode: 6090
                         Secure TCP Command Mode: 6091
                         FTP: 21
                         FTP Data: 20
                         TFTP: 69
                         SLP: 427
                         CIM: 5989 

                      NOTE: Value returned for the GET command is meaningless for this MIB object."
                      ::= { tcpPortAssignmentCfg 1 }

         httpPortAssignment   OBJECT-TYPE
                      SYNTAX  INTEGER
                      ACCESS  read-write
                      STATUS  mandatory
                      DESCRIPTION
                      "HTTP port number. Default value is 80. Once changed, the URL's have to
                      include :port at the end."
                      ::= { tcpPortAssignmentCfg 2 }

         httpsPortAssignment   OBJECT-TYPE
                      SYNTAX  INTEGER
                      ACCESS  read-write
                      STATUS  mandatory
                      DESCRIPTION
                      "SSL port number. Default value is 443. Once changed, the URL's have to
                      include :port at the end."
                      ::= { tcpPortAssignmentCfg 3 }

         telnetPortAssignment   OBJECT-TYPE
                      SYNTAX  INTEGER
                      ACCESS  read-write
                      STATUS  mandatory
                      DESCRIPTION
                      "Telnet port number. Default value is 23. Port change will take effect immediately."
                      ::= { tcpPortAssignmentCfg 4 }

         sshPortAssignment   OBJECT-TYPE
                      SYNTAX  INTEGER
                      ACCESS  read-write
                      STATUS  mandatory
                      DESCRIPTION
                      "SSH port number. Default value is 22."
                      ::= { tcpPortAssignmentCfg 5 }

         snmpAgentPortAssignment   OBJECT-TYPE
                      SYNTAX  INTEGER
                      ACCESS  read-write
                      STATUS  mandatory
                      DESCRIPTION
                      "SNMP Agent port number. Default value is 161.
                      Changes take effect after several seconds."
                      ::= { tcpPortAssignmentCfg 6 }

         snmpTrapsPortAssignment   OBJECT-TYPE
                      SYNTAX  INTEGER
                      ACCESS  read-write
                      STATUS  mandatory
                      DESCRIPTION
                      "SNMP Traps port number. Default value is 162.
                      Changes take effect after several seconds."
                      ::= { tcpPortAssignmentCfg 7 }

        commandModePortAssignment    OBJECT-TYPE
                      SYNTAX  INTEGER
                      ACCESS  read-write
                      STATUS  mandatory
                      DESCRIPTION
                      "TCP Command Mode port number. Default value is 6090. Change will take effect immediately."
                      ::= { tcpPortAssignmentCfg 8 }

        secureCommandModePortAssignment    OBJECT-TYPE
                      SYNTAX  INTEGER
                      ACCESS  read-write
                      STATUS  mandatory
                      DESCRIPTION
                      "Secure TCP Command Mode port number. Default value is 6091. Change will take effect immediately."
                      ::= { tcpPortAssignmentCfg 9 }

         ftpPortAssignment   OBJECT-TYPE
                      SYNTAX  INTEGER
                      ACCESS  read-write
                      STATUS  mandatory
                      DESCRIPTION
                      "FTP port number. Default value is 21. Port change will take effect immediately."
                      ::= { tcpPortAssignmentCfg 13 }

         ftpDataPortAssignment   OBJECT-TYPE
                      SYNTAX  INTEGER
                      ACCESS  read-write
                      STATUS  mandatory
                      DESCRIPTION
                      "FTP Data port number. Default value is 20. Port change will take effect immediately."
                      ::= { tcpPortAssignmentCfg 14 }

         tftpPortAssignment   OBJECT-TYPE
                      SYNTAX  INTEGER
                      ACCESS  read-write
                      STATUS  mandatory
                      DESCRIPTION
                      "TFTP port number. Default value is 69."
                      ::= { tcpPortAssignmentCfg 15 }

         slpPortAssignment   OBJECT-TYPE
                      SYNTAX  INTEGER
                      ACCESS  read-write
                      STATUS  mandatory
                      DESCRIPTION
                      "Service Location Protocol port number. Default value is 427.
                      NOTE: This value is normally required to be 427 to interoperate properly
                      with other SLP enabled applications."
                      ::= { tcpPortAssignmentCfg 19 }

         cimPortAssignment   OBJECT-TYPE
                      SYNTAX  INTEGER
                      ACCESS  read-write
                      STATUS  mandatory
                      DESCRIPTION
                      "CIM (Common Information Model) port number. Default value is 5989.
                      Port change will take effect immediately."
                      ::= { tcpPortAssignmentCfg 50 }

        -- LDAP Client Configuration
        ldapClientCfg    OBJECT IDENTIFIER ::= { tcpProtocols 6 }

         ldapServer1NameOrIPAddress     OBJECT-TYPE
                      SYNTAX  OCTET STRING (SIZE(0..256))
                      ACCESS  read-write
                      STATUS  mandatory
                      DESCRIPTION
                      "A NULL terminated 255 byte string that contains the
                      LDAP server host name or IP address (a.b.c.d)."
                      ::= { ldapClientCfg 1 }

         ldapServer1PortNumber   OBJECT-TYPE
                      SYNTAX  INTEGER
                      ACCESS  read-write
                      STATUS  mandatory
                      DESCRIPTION
                      "LDAP server port number."
                      ::= { ldapClientCfg 2 }

         ldapServer2NameOrIPAddress     OBJECT-TYPE
                      SYNTAX  OCTET STRING (SIZE(0..256))
                      ACCESS  read-write
                      STATUS  mandatory
                      DESCRIPTION
                      "A NULL terminated 255 byte string that contains the
                      LDAP server host name or IP address (a.b.c.d)."
                      ::= { ldapClientCfg 3 }

         ldapServer2PortNumber   OBJECT-TYPE
                      SYNTAX  INTEGER
                      ACCESS  read-write
                      STATUS  mandatory
                      DESCRIPTION
                      "LDAP server port number."
                      ::= { ldapClientCfg 4 }

         ldapServer3NameOrIPAddress     OBJECT-TYPE
                      SYNTAX  OCTET STRING (SIZE(0..256))
                      ACCESS  read-write
                      STATUS  mandatory
                      DESCRIPTION
                      "A NULL terminated 255 byte string that contains the
                      LDAP server host name or IP address (a.b.c.d)."
                      ::= { ldapClientCfg 5 }

         ldapServer3PortNumber   OBJECT-TYPE
                      SYNTAX  INTEGER
                      ACCESS  read-write
                      STATUS  mandatory
                      DESCRIPTION
                      "LDAP server port number."
                      ::= { ldapClientCfg 6 }

         ldapRootDN     OBJECT-TYPE
                      SYNTAX  OCTET STRING (SIZE(0..256))
                      ACCESS  read-write
                      STATUS  mandatory
                      DESCRIPTION
                      "A NULL terminated 255 byte string that contains the
                      distinguished Name for root entry of directory tree.
                      An example might look like dn=foobar,dn=com."
                      ::= { ldapClientCfg 7 }

         ldapGroupFilter     OBJECT-TYPE
                      SYNTAX  OCTET STRING (SIZE(0..511))
                      ACCESS  read-write
                      STATUS  mandatory
                      DESCRIPTION
                      "This filter is used for group authentication. It specifies what group or
                      groups that this MM belongs to. If left blank, group authentication is
                      disabled. Otherwise, group authentication will be performed against the
                      filter. The filter can be a specific group name (e.g. RSAWest), a wildcard (*)
                      which matches everything, or a wildcard with a prefix (e.g. RSA*). The default
                      filter is RSA*.
                      After user authentication, group authentication will take place, whereby an
                      attempt will be made to match the group or groups (that the user belongs to)
                      to the group filter defined here. If there is no match, the user will not pass
                      authentication and will be blocked. If there is a match, the login permissions
                      for the user will be retrieved from the matched group(s), unless the user
                      already has login permissions assigned directly from the user record retrieved
                      from the LDAP server."
                      ::= { ldapClientCfg 9 }

         ldapBindingMethod  OBJECT-TYPE
                      SYNTAX  INTEGER {
                        clientAuthentication(1),
                        userPrincipalName(2)
                      }
                      ACCESS  read-write
                      STATUS  mandatory
                      DESCRIPTION
                      "On initial binds to the LDAP server during user authentication, there are
                      two options:
                      Client authentication: Bind attempt is made with client DN and password
                      specified by this configuration parameter. If the bind is successful, we
                      proceed as above.
                      User Principal Name (UPN): Bind attempt is made directly with the credentials
                      used during the login process. If this succeeds, the user is deemed to have
                      passed the user authentication phase. Note that for Active Directory servers,
                      the userid can have the form someuser@somedomain or simply someuser."
                      ::= { ldapClientCfg 10 }

         ldapClientAuthenticationDN     OBJECT-TYPE
                      SYNTAX  OCTET STRING (SIZE(0..64))
                      ACCESS  read-write
                      STATUS  mandatory
                      DESCRIPTION
                      "The initial bind to the LDAP server during user authentication can be
                      performed with anonymous authentication, client based authentication, or UPN.
                      The client based option requires a client DN and password as parameters to
                      the bind request. These parameters are configured here. Note that the password
                      can be left blank."
                      ::= { ldapClientCfg 11 }

         ldapClientAuthenticationPassword     OBJECT-TYPE
                      SYNTAX  OCTET STRING (SIZE(0..16))
                      ACCESS  read-write
                      STATUS  mandatory
                      DESCRIPTION
                      "The client authentication password"
                      ::= { ldapClientCfg 12 }

         ldapUIDsearchAttribute     OBJECT-TYPE
                      SYNTAX  OCTET STRING (SIZE(0..64))
                      ACCESS  read-write
                      STATUS  mandatory
                      DESCRIPTION
                      "When the binding method selected is Anonymous authentication or Client
                      authentication, the initial bind to the LDAP server is followed by a search
                      request aimed at retrieving specific information about the user, including the
                      user's DN, login permissions, and group ownerships. In order to retrieve this
                      information, the search request must specify the attribute name used to
                      represent userids on that server. Specifically, this name is used as a search
                      filter against the login id entered by the user. This attribute name is
                      configured here. If this field is left blank, a default of uid is used during
                      user authentication.
                      For example, on Active Directory servers, the attribute name used for userids
                      is often sAMAccoutName.
                      When the binding method selected is UPN or Strict UPN, this field defaults
                      automatically to userPrincipalName during user authentication if the userid
                      entered has the form userid@somedomain."
                      ::= { ldapClientCfg 13 }

         ldapGroupSearchAttribute     OBJECT-TYPE
                      SYNTAX  OCTET STRING (SIZE(0..64))
                      ACCESS  read-write
                      STATUS  mandatory
                      DESCRIPTION
                      "When the MM Group Filter name is configured, it is necessary to retrieve
                      from the LDAP server the list of groups that a particular user belongs to.
                      This is required to do group authentication. In order to retrieve this list,
                      the search filter sent to the server must specify the attribute name associated
                      with groups. This field specifies this attribute name.
                      If this field is left blank, the attribute name in the filter will default
                      to memberOf."
                      ::= { ldapClientCfg 14 }

         ldapLoginPermissionAttribute     OBJECT-TYPE
                      SYNTAX  OCTET STRING (SIZE(0..64))
                      ACCESS  read-write
                      STATUS  mandatory
                      DESCRIPTION
                      "When a user successfully authenticates via a LDAP server, it is necessary
                      to retrieve the login permissions for this user. In order to retrieve these
                      permissions, the search filter sent to the server must specify the attribute
                      name associated with login permissions. This field specifies this attribute
                      name."
                      ::= { ldapClientCfg 15 }

         ldapUseDNSOrPreConfiguredServers     OBJECT-TYPE
                      SYNTAX  INTEGER {
                        usePreConfiguredLDAPServers (0),
                        useDNSToFindLDAPServers (1)
                      }
                      ACCESS  read-write
                      STATUS  mandatory
                      DESCRIPTION
                      "The MM contains a Version 2.0 LDAP Client that may be configured to provide
                      user authentication through one or more LDAP servers. The LDAP server(s) to be
                      used for authentication can be discovered dynamically or manually pre-configured.

                      If the usePreConfiguredLDAPServers option is selected, up to 4 LDAP servers can
                      be configured. Simply enter the server's IP address or hostname (assuming DNS
                      is enabled).  The port number for each server is optional. If left blank,
                      the default value of 389 is used for non-secured LDAP connections. For secured
                      connections, the default is 636. At least one server must be configured.

                      If the useDNSToFindLDAPServers is selected, the domain name need to be provided.
                      For LDAP Authentication Only mode, additional information such as the forest name
                      also need to be provided."
                      ::= { ldapClientCfg 16 }

         ldapRBSModelCfg     OBJECT-TYPE
                      SYNTAX  INTEGER {
                        oldPermissionString(0),
                        newRBSModel(1)
                      }
                      ACCESS  read-write
                      STATUS  mandatory
                      DESCRIPTION
                      "There are two mechanisms to authenticate and authorize users on the MM when
                      using an LDAP-enabled server. The first mechanism (oldPermissionString), also
                      known as version 1, uses bitstrings to associate permissions to users and groups.
                      Version1 supports Active Directory, Novell eDirectory, and OPenLDAP based
                      servers.  The second mechanism (newRBSModel),  also known as version 2,
                      uses a new Role-Based-Security (RBS) model. This mechanism is only available
                      for Active Directory servers, and requires the use of a snap-in that runs on any
                      windows platform. This snap-in tool allows you to configure roles on an Active
                      Directory server of your choice, and to associate users/groups and MMs to those
                      roles. A role identifies the permissions given to users and groups associated with
                      that role, and also identifies the targets (e.g. MM) to which this role is attached.
                      The use of bitstrings in version 2 disappears, making the configuration much more
                      manageable and user-friendly. Note that if you are not using Active Directory, then
                      you should not enable version 2. Also note that before enabling version 2, you should
                      already have your roles configured on your Active Directory server. The old version 1
                      bitstring model cannot be automatically converted to the new version 2 model. This is
                      why you must configure your users and groups before enabling version 2. Once
                      enabled, the change takes effect immediately. The default value for this field is
                      oldPermissionString."
                      ::= { ldapClientCfg 20 }

         ldapTargetName     OBJECT-TYPE
                      SYNTAX  OCTET STRING (SIZE(0..16))
                      ACCESS  read-write
                      STATUS  mandatory
                      DESCRIPTION
                      "When administrator chooses Enhanced Role Based Security authentication model,
                      he can associate  one MM with one managed target object in Snap-in (one tool
                      to configure LDAP users permission) via one target name. The MM target name can
                      be looked as alias of MM, administrator can change it according to his
                      configuration requirements. This is a string of up to 63 characters (plus the
                      null character)"
                      ::= { ldapClientCfg 21 }

        ldapAuthCfg     OBJECT-TYPE
                      SYNTAX  INTEGER {
                        authenticationAndAuthorization(0),
                        authenticationOnly(1)
                      }
                      ACCESS  read-write
                      STATUS  mandatory
                      DESCRIPTION
                      "If ldapAuthCfg is set to 0, LDAP server is used to authenticate and authorize
                      users. If it is set to 1, LDAP server is only used to authenticate users.

                      Note:LDAP Authentication Only mode is currently supported only in an Active
                      Directory environment."
                      ::= { ldapClientCfg 22 }

        ldapForestName     OBJECT-TYPE
                      SYNTAX  OCTET STRING (SIZE(0..64))
                      ACCESS  read-write
                      STATUS  mandatory
                      DESCRIPTION
                      "LDAP Forest Name.

                      Note: LDAP Forest Name is only for Active Directory environment."
                      ::= { ldapClientCfg 23 }

        ldapDomainName     OBJECT-TYPE
                      SYNTAX  OCTET STRING (SIZE(0..256))
                      ACCESS  read-write
                      STATUS  mandatory
                      DESCRIPTION
                      "A NULL terminated 255 byte string that contains the 
                       LDAP Domain Name."
                      ::= { ldapClientCfg 24 }

         ldapServer4NameOrIPAddress     OBJECT-TYPE
                      SYNTAX  OCTET STRING (SIZE(0..256))
                      ACCESS  read-write
                      STATUS  mandatory
                      DESCRIPTION
                      "A NULL terminated 255 byte string that contains the
                      LDAP server host name or IP address (a.b.c.d)."
                      ::= { ldapClientCfg 25 }

         ldapServer4PortNumber   OBJECT-TYPE
                      SYNTAX  INTEGER
                      ACCESS  read-write
                      STATUS  mandatory
                      DESCRIPTION
                      "LDAP server port number."
                      ::= { ldapClientCfg 26 }

        -- ********************************************************************************
        -- Uplink Check Configuration
        -- ********************************************************************************

        uplinkCheckConfig  OBJECT IDENTIFIER ::= { tcpProtocols 7 }

         physicalUplinkCheckEnabled   OBJECT-TYPE
                      SYNTAX  INTEGER {
                        uplinkCheckDisabled(0),
                        uplinkCheckEnabled(1)
                      }
                      ACCESS  read-write
                      STATUS  mandatory
                      DESCRIPTION
                      "Disable or enable network uplink checking for physical detection.

                      NOTE: This MIB object is only applicable to systems with a standby MM."
                      ::= { uplinkCheckConfig 1 }

         physicalUplinkCheckDelayInMins   OBJECT-TYPE
                      SYNTAX  INTEGER
                      ACCESS  read-write
                      STATUS  mandatory
                      DESCRIPTION
                      "Delay, in minutes (1-2880), between discovery of a failed network uplink and
                      the subsequent MM failover for physical detection.

                      NOTE: This MIB object is only applicable to systems with a standby MM."
                      ::= { uplinkCheckConfig 2 }

         logicalUplinkIPv4Destination    OBJECT-TYPE
                      SYNTAX  IpAddress
                      ACCESS  read-write
                      STATUS  mandatory
                      DESCRIPTION
                      "Destination IP for MM to check its logical link.
                      Specify a non-zero IP Address in order to enable logical uplink checking.

                      NOTE: This MIB object is only applicable to systems with a standby MM."
                      ::= { uplinkCheckConfig 3 }

         logicalUplinkCheckEnabled   OBJECT-TYPE
                      SYNTAX  INTEGER {
                        uplinkCheckDisabled(0),
                        uplinkCheckEnabled(1)
                      }
                      ACCESS  read-write
                      STATUS  mandatory
                      DESCRIPTION
                      "Disable or enable network uplink checking for logical detection.
                      logicalUplinkDestination must be set to a non-zero IP Address before enable
                      logical uplink checking.

                      NOTE: This MIB object is only applicable to systems with a standby MM."
                      ::= { uplinkCheckConfig 4 }

         logicalUplinkCheckDelayInMins   OBJECT-TYPE
                      SYNTAX  INTEGER
                      ACCESS  read-write
                      STATUS  mandatory
                      DESCRIPTION
                      "Delay, in minutes(1-2880), between discovery of a failed network uplink and
                      the subsequent MM failover for logical detection.

                      NOTE: This MIB object is only applicable to systems with a standby MM."
                      ::= { uplinkCheckConfig 5 }

         physicalUplinkCheckDelayInSecs   OBJECT-TYPE
                      SYNTAX  INTEGER
                      ACCESS  read-write
                      STATUS  mandatory
                      DESCRIPTION
                      "Delay, in seconds(10-172800), between discovery of a failed network uplink and
                      the subsequent MM failover for physical detection.

                      NOTE: This MIB object is only applicable to systems with a standby MM."
                      ::= { uplinkCheckConfig 6 }

         logicalUplinkCheckDelayInSecs   OBJECT-TYPE
                      SYNTAX  INTEGER
                      ACCESS  read-write
                      STATUS  mandatory
                      DESCRIPTION
                      "Delay, in seconds(60-172800), between discovery of a failed network uplink and
                      the subsequent MM failover for logical detection.

                      NOTE: This MIB object is only applicable to systems with a standby MM."
                      ::= { uplinkCheckConfig 7 }

         logicalUplinkIPv6Destination    OBJECT-TYPE
                      SYNTAX  InetAddressIPv6
                      ACCESS  read-write
                      STATUS  mandatory
                      DESCRIPTION
                      "Destination IP for MM to check its logical link using IPv6.
                      Specify a non-zero IP Address in order to enable logical uplink checking.

                      NOTE: This MIB object is only applicable to systems with a standby MM."
                      ::= { uplinkCheckConfig 8 }

         logicalUplinkFailoverPolicy    OBJECT-TYPE
                      SYNTAX  INTEGER { either(1), both(2) }
                      ACCESS  read-write
                      STATUS  mandatory
                      DESCRIPTION
                      "Determines when to failover if both an IPv4 and IPv6 destination
                      have been configured.

                      If set to 'either' the system will failover if either of the
                      destination's link check fails. If set to 'both' then the IPv4
                      and IPv6 link checks must fail before a failover will happen.

                      NOTE: This MIB object is only applicable to systems with a standby MM."
                      ::= { uplinkCheckConfig 9 }

        -- ********************************************************************************
        -- NTP Configuration
        -- ********************************************************************************
        ntpConfig  OBJECT IDENTIFIER ::= { tcpProtocols 8 }

         ntpEnable    OBJECT-TYPE
                      SYNTAX  INTEGER {
                        disabled(0),
                        enabled(1)
                      }
                      ACCESS  read-write
                      STATUS  mandatory
                      DESCRIPTION
                      "Disable/Enable the NTP client.  The client will update
                      the MM system clock at the frequency specified."
                      ::= { ntpConfig 1 }

         ntpIpAddressHostname  OBJECT-TYPE
                      SYNTAX  OCTET STRING (SIZE(0..63))
                      ACCESS  read-write
                      STATUS  mandatory
                      DESCRIPTION
                      "NTP server's IP address or hostname if DNS is enabled
                      and configured."
                      ::= { ntpConfig 2 }

         ntpUpdateFrequency  OBJECT-TYPE
                      SYNTAX  INTEGER
                      ACCESS  read-write
                      STATUS  mandatory
                      DESCRIPTION
                      "The frequency in minutes that the NTP service runs.
                      The value range is a set of fixed values mandated by the NTP 
                      service, including 0, 1, 2, 4, 8, 17, 34, 68, 136, 273, 546, 
                      1092, 2184, 4369, 8738, 17476, 34952. If the NTP update frequency
                      is set to 0, the MM clock can only be synchronized with the
                      NTP server manually."
                      ::= { ntpConfig 3 }

         ntpLastUpdate  OBJECT-TYPE
                      SYNTAX  OCTET STRING
                      ACCESS  read-only
                      STATUS  mandatory
                      DESCRIPTION
                      "The date and time that the NTP server last updated
                      the system clock."
                      ::= { ntpConfig 4 }

         ntpUpdateClock  OBJECT-TYPE
                      SYNTAX  INTEGER  {
                        execute(1)
                      }
                      ACCESS  read-write
                      STATUS  mandatory
                      DESCRIPTION
                      "Update the MM system clock with the specified NTP server.
                      A valid NTP server must be configured first."
                      ::= { ntpConfig 5 }

         ntpAuthEntry  OBJECT-TYPE
                      SYNTAX  OCTET STRING
                      ACCESS  read-write
                      STATUS  mandatory
                      DESCRIPTION
                      "The NTP v3 authentication entry to be used for time sync
                      with a secure NTP server. The format of an authentication
                      entry is <key index> <key type> <key>. <key index> must
                      be an integer between 1 and 65535. <key type> must be
                      M. <key> is the actual value of the authentication
                      key as configured on the NTP server.
                      The GET command returns back data in the format:
                      <key index> <key type>
                      It does not return the actual key."
                      ::= { ntpConfig 6 }

         ntpAuthEnable  OBJECT-TYPE
                      SYNTAX  INTEGER {
                        disabled(0),
                        enabled(1)
                      }
                      ACCESS  read-write
                      STATUS  mandatory
                      DESCRIPTION
                      "Enables/Disables NTP v3 authentication"
                      ::= { ntpConfig 7 }

        -- ********************************************************************************
        -- SYSLOG Configuration
        -- ********************************************************************************
        syslogConfig  OBJECT IDENTIFIER ::= { tcpProtocols 9 }

        syslogSevFilterLevel  OBJECT-TYPE
                    SYNTAX  INTEGER {
                      error(0),
                      warning(1),
                      information(2)
                    }
                    ACCESS  read-write
                    STATUS  mandatory
                    DESCRIPTION
                    "syslogSevFilterLevel    error/warning/information ."
                    ::= { syslogConfig 1 }

         -- ********************************************************************************
         -- syslogCollector   Configuration
         -- ********************************************************************************
         syslogCollectorConfig  OBJECT IDENTIFIER ::= { syslogConfig 2 }

          -- ********************************************************************************
          -- Syslog Collector Configuration table
          -- ********************************************************************************

          syslogCollectorTable  OBJECT-TYPE
                                SYNTAX  SEQUENCE OF SyslogCollectorEntry
                                ACCESS  not-accessible
                                STATUS  mandatory
                                DESCRIPTION
                                "Table of Syslog Collector entries"
                                ::= {  syslogCollectorConfig 1 }

          syslogCollectorEntry  OBJECT-TYPE
                                SYNTAX  SyslogCollectorEntry
                                ACCESS  not-accessible
                                STATUS  mandatory
                                DESCRIPTION
                                "Syslog Collector entries"
                                INDEX { syslogCollectorIndex }
                                ::= { syslogCollectorTable 1 }

          SyslogCollectorEntry ::= SEQUENCE {
                       syslogCollectorIndex INTEGER,
                       syslogCollectorHostnameOrIpAddress OCTET STRING,
                       syslogCollectorPort INTEGER,
                       syslogCollectorEnable INTEGER
                       }

          syslogCollectorIndex   OBJECT-TYPE
                                    SYNTAX  INTEGER(0..255)
                                    ACCESS  read-only
                                    STATUS  mandatory
                                    DESCRIPTION
                                    "Index for Syslog Collector entry."
                                    ::= { syslogCollectorEntry 1 }

          syslogCollectorHostnameOrIpAddress  OBJECT-TYPE
                                    SYNTAX  OCTET STRING (SIZE(0..63))
                                    ACCESS  read-write
                                    STATUS  mandatory
                                    DESCRIPTION
                                    "Syslog Collector IP address or host name."
                                    ::= { syslogCollectorEntry 2 }

          syslogCollectorPort   OBJECT-TYPE
                                    SYNTAX  INTEGER(1..65535)
                                    ACCESS  read-write
                                    STATUS  mandatory
                                    DESCRIPTION
                                    "Syslog Collector port number."
                                    ::= { syslogCollectorEntry 3 }

          syslogCollectorEnable   OBJECT-TYPE
                                    SYNTAX  INTEGER {
                                      disabled(0),
                                      enabled(1)
                                    }
                                    ACCESS  read-write
                                    STATUS  mandatory
                                    DESCRIPTION
                                    "Syslog Collector enable/disable."
                                    ::= { syslogCollectorEntry 4 }

         -- ********************************************************************************
         -- Generate test syslog packet
         -- ********************************************************************************
         syslogTestPacket  OBJECT-TYPE
                   SYNTAX  INTEGER {
                    execute(1)
                   }
                   ACCESS  read-write
                   STATUS  mandatory
                   DESCRIPTION
                   "Generate a test syslog packet. This will send a test syslog to all configured
                    and enabled syslog collectors to assist in validating the configuration.

                    NOTE: Value returned for the GET command is meaningless for this
                          MIB object."
                    ::= { syslogConfig 3 }

       -- ********************************************************************************
       -- SOL (Serial Over LAN) Configuration
       -- ********************************************************************************
       solConfiguration  OBJECT IDENTIFIER ::= { configureSP 10 }

        -- ********************************************************************************
        -- SOL Global Configuration
        -- ********************************************************************************
        solGlobalConfig  OBJECT IDENTIFIER ::= { solConfiguration 1 }

         solEnable  OBJECT-TYPE
                    SYNTAX  INTEGER {
                      solDisabled(0),
                      solEnabled(1)
                    }
                    ACCESS  read-write
                    STATUS  mandatory
                    DESCRIPTION
                    "Disable/Enable SOL dynamically."
                    ::= { solGlobalConfig 1 }

         solAccumulateTimeout  OBJECT-TYPE
                    SYNTAX  INTEGER
                    ACCESS  read-write
                    STATUS  mandatory
                    DESCRIPTION
                    "This value specifies how much time in millisecond SOL to buffer data before
                    sending the next SOL packet since the last SOL packet was transmitted.
                    Valid value from 5 ms to 1275 ms. The value is in 5 ms increment. Value
                    is not in 5 ms increment will be truncated to a nearest 5s. Default value
                    is 5 ms."
                    ::= { solGlobalConfig 3 }

         solCharSendThreshold  OBJECT-TYPE
                    SYNTAX  INTEGER
                    ACCESS  read-write
                    STATUS  mandatory
                    DESCRIPTION
                    "This value specifies how many characters SOL to buffer before
                    sending the next SOL packet since the last SOL packet was transmitted.
                    Valid value is from 1 to 251"
                    ::= { solGlobalConfig 4 }

         solRetry  OBJECT-TYPE
                    SYNTAX  INTEGER
                    ACCESS  read-write
                    STATUS  mandatory
                    DESCRIPTION
                    "Retry count. Valid value from 0-7. 0 means no retries after packet is transmitted.
                    Packet will be dropped if no ACK/NACK received by the time retries expired."
                    ::= { solGlobalConfig 5 }

         solRetryInterval  OBJECT-TYPE
                    SYNTAX  INTEGER
                    ACCESS  read-write
                    STATUS  mandatory
                    DESCRIPTION
                    "Retry Interval in 10 ms increment. Sets the time that the SOL will
                    wait before the first retry and the time between retries when sending SOL
                    packets to the remote blade. Value range is from 0 to 2550 ms in 10 ms
                    increment. 0 means retries will be sent back-to-back."
                    ::= { solGlobalConfig 6 }

      solExitToCliKeySeq  OBJECT-TYPE
                    SYNTAX  OCTET STRING(SIZE(0..16))
                    ACCESS  read-write
                    STATUS  mandatory
                    DESCRIPTION
                    "This is the keystroke sequence used to escape out of SOL session and back to CLI
                    console. This sequence must have at least one character. The caret symbol (^)
                    has a special meaning in this sequence. It denotes 'Ctrl' for keystrokes that
                    map to Ctrl sequences (for example, ^[ for the escape key and ^M for carriage
                    return). All occurrences of ^ will be interpreted as part of a Ctrl sequence.
                    Refer to an ASCII-to-key conversion table for a complete list of Ctrl sequences.
                    The default value for this field is '^[(' i.e. ESC followed by (."
                    ::= { solGlobalConfig 7 }

      solResetBladeKeySeq  OBJECT-TYPE
                    SYNTAX  OCTET STRING(SIZE(0..16))
                    ACCESS  read-write
                    STATUS  mandatory
                    DESCRIPTION
                    "This is the keystroke sequence used to reset the blade while in SOL session
                    console. This sequence must have at least one character. The caret symbol (^)
                    has a special meaning in this sequence. It denotes 'Ctrl' for keystrokes that
                    map to Ctrl sequences (for example, ^[ for the escape key and ^M for carriage
                    return). All occurrences of ^ will be interpreted as part of a Ctrl sequence.
                    Refer to an ASCII-to-key conversion table for a complete list of Ctrl sequences.
                    The default value for this field is '^[R^[r^[R' i.e. ESC R ESC r ESC R."
                    ::= { solGlobalConfig 8 }

         --  Blade SOL config
         solBladeConfig  OBJECT IDENTIFIER ::= { solConfiguration 2 }

         solBladeTable OBJECT-TYPE
                    SYNTAX  SEQUENCE OF SolBladeEntry
                    ACCESS  not-accessible
                    STATUS  mandatory
                    DESCRIPTION
                    "SOL Blade configuration table."
                    ::= { solBladeConfig 1 }

         solBladeEntry  OBJECT-TYPE
                    SYNTAX  SolBladeEntry
                    ACCESS  not-accessible
                    STATUS  mandatory
                    DESCRIPTION
                    "SOL Blade table entry"
                    INDEX { solBladeIndex }
                    ::= { solBladeTable 1 }

         SolBladeEntry ::= SEQUENCE {
                    solBladeIndex   INTEGER,
                    solBladeName    OCTET STRING,
                    solBladeEnable  INTEGER,
                    solBladeIpAddr  IpAddress,
                    solBladeSessionStatus  INTEGER,
                    solBladeCapability  INTEGER,
		    solBladeIpAddr6   InetAddressIPv6,
                    solBladeRetryInterval INTEGER,
		    solBladeRetryCount INTEGER,
		    solBladeBytesSent INTEGER,
		    solBladeBytesReceived INTEGER,
		    solBladeDestinationMAC OCTET STRING,
		    solBladeConsoleUserId OCTET STRING,
	            solBladeConsoleLoginFrom OCTET STRING,
		    solBladeConsoleLoginStart OCTET STRING,
		    solBladeConsoleLoginEnd OCTET STRING
                    }

         solBladeIndex OBJECT-TYPE
                    SYNTAX  INTEGER
                    ACCESS  read-only
                    STATUS  mandatory
                    DESCRIPTION
                    "SOL Blade table index."
                    ::= { solBladeEntry 1 }

         solBladeName OBJECT-TYPE
                    SYNTAX  OCTET STRING
                    ACCESS  read-only
                    STATUS  mandatory
                    DESCRIPTION
                    "The name of the blade as a null terminated string."
                    ::= { solBladeEntry 2 }

         solBladeEnable  OBJECT-TYPE
                    SYNTAX  INTEGER {
                      solBladeDisabled(0),
                      solBladeEnabled(1)
                    }
                    ACCESS  read-write
                    STATUS  mandatory
                    DESCRIPTION
                    "Disable or enable a SOL on a blade."
                    ::= { solBladeEntry 3 }

         solBladeIpAddr   OBJECT-TYPE
                    SYNTAX  IpAddress
                    ACCESS  read-only
                    STATUS  deprecated
                    DESCRIPTION
                    " This is deprecated in favor of solBladeIpAddr6.
		    IP address of the blade derived from the IP address range for the blade
                    system management processors on the blades.

                    NOTE: The IPv6 address for a blade can be view with the
                    bladeIPv6AddressTable."
                    ::= { solBladeEntry 4 }

         solBladeSessionStatus OBJECT-TYPE
                    SYNTAX  INTEGER {
                      solSessionNotReady(0),
                      solSessionReady(1),
                      solSessionActive(2)
                    }
                    ACCESS  read-only
                    STATUS  mandatory
                    DESCRIPTION
                    "Status of a blade SOL session:
                       solSessionNotReady: no SOL session connected to the blade.
                       solSessionReady: there is an SOL session to the blade.
                       solSessionActive: there is an SOL session to the blade and there is a
                       client using the SOL session."
                    ::= { solBladeEntry 5 }

         solBladeCapability OBJECT-TYPE
                    SYNTAX  INTEGER {
                      notSupport(0),
                      support(1)
                    }
                    ACCESS  read-only
                    STATUS  mandatory
                    DESCRIPTION
                    "Display whether or not the blade support SOL feature."
                    ::= { solBladeEntry 6 }

	 solBladeIpAddr6 OBJECT-TYPE
		    SYNTAX InetAddressIPv6
		    ACCESS read-only
		    STATUS mandatory
		    DESCRIPTION
		    " IPv6 address of the blade."
		    ::= { solBladeEntry 7 }

	 solBladeRetryInterval OBJECT-TYPE
		    SYNTAX INTEGER
		    ACCESS read-only
		    STATUS mandatory
		    DESCRIPTION
		    " Retry interval time in miliseconds."
		    ::={solBladeEntry 8}

	 solBladeRetryCount OBJECT-TYPE
		    SYNTAX INTEGER
		    ACCESS read-only
		    STATUS mandatory
		    DESCRIPTION
		    " Retry count."
		    ::={solBladeEntry 9}

	 solBladeBytesSent OBJECT-TYPE
		    SYNTAX INTEGER
		    ACCESS read-only
		    STATUS mandatory
		    DESCRIPTION
		    " Number of bytes sent."
		    ::={solBladeEntry 10}

	 solBladeBytesReceived  OBJECT-TYPE
		   SYNTAX INTEGER
		   ACCESS read-only
		   STATUS mandatory
		   DESCRIPTION
		   " Number of bytes received."
		   ::={solBladeEntry 11}

	 solBladeDestinationMAC OBJECT-TYPE
		   SYNTAX OCTET STRING
		   ACCESS read-only
		   STATUS mandatory
		   DESCRIPTION
		   " MAC address of the blade."
		   ::={solBladeEntry 12}

	 solBladeConsoleUserId OBJECT-TYPE
		   SYNTAX OCTET STRING
		   ACCESS read-only
		   STATUS mandatory
		   DESCRIPTION
		   " Sol console user name."
		   ::={solBladeEntry 13}

	 solBladeConsoleLoginFrom OBJECT-TYPE
		   SYNTAX OCTET STRING
		   ACCESS read-only
		   STATUS mandatory
		   DESCRIPTION
		   " The location information from where the SOL console is logged in. "
		   ::={solBladeEntry 14}

	 solBladeConsoleLoginStart OBJECT-TYPE
		   SYNTAX OCTET STRING
		   ACCESS read-only
		   STATUS mandatory
		   DESCRIPTION
		   " The time that SOL console starts. "
		   ::={solBladeEntry 15}

	 solBladeConsoleLoginEnd OBJECT-TYPE
		   SYNTAX OCTET STRING
		   ACCESS read-only
		   STATUS mandatory
		   DESCRIPTION
		   " The time that SOL console ends. "
		   ::={solBladeEntry 16}



 	  -- ********************************************************************************
          -- Chassis Internal Network (CIN)
          -- ********************************************************************************
	  chassisInternalNetwork OBJECT IDENTIFIER ::= { configureSP 11}

          -- Maximum number of CIN definitions supported
	  cinsSupported  OBJECT-TYPE
	            SYNTAX  INTEGER
		    ACCESS  read-only
		    STATUS  mandatory
		    DESCRIPTION
		    "Number of Chassis Internal Network (CIN) definitions supported.
		    Currently a maximum of 14 CIN definitions can be supported."
		    ::= { chassisInternalNetwork 1 }

          -- CIN Global Configuration
	  cinGlobalEnable  OBJECT-TYPE
	            SYNTAX  INTEGER {
		      cinDisabled(0),
		      cinEnabled(1)
		    }
		    ACCESS  read-write
		    STATUS  mandatory
		    DESCRIPTION
		    "Disable/Enable Chassis Internal Network (CIN) function dynamically.
                       Enabled:
                         MM reads the CIN entries. For each enabled entry,
                           - If the CIN VLAN ID is new and does not have a CIN interface
                             created yet then create a new CIN interface based on that
                             CIN VLAN ID. Use the CIN IP address from the entry to create
                             a host route.
                           - If the CIN IP address is 0.0.0.0 then start ARP monitoring.

                         Disabled:
                            - Stop all ARP monitoring.
                            - Delete all host routes.
                            - Delete all CIN interfaces."
		    ::= { chassisInternalNetwork 2 }

          -- CIN Configuration Table
	  cinTable  OBJECT-TYPE
	            SYNTAX  SEQUENCE OF CinEntry
		    ACCESS  not-accessible
		    STATUS  mandatory
		    DESCRIPTION
		    "Chassis Internal Network (CIN) configuration table."
		    ::= { chassisInternalNetwork 3}

	     cinEntry  OBJECT-TYPE
	            SYNTAX  CinEntry
		    ACCESS  not-accessible
		    STATUS  mandatory
		    DESCRIPTION
		    "Chassis Internal Network (CIN) table entry."
                    INDEX { cinIndex }
		    ::= { cinTable 1 }

             CinEntry ::= SEQUENCE {
	            cinIndex  INTEGER,
		    cinDefExists INTEGER,
	            cinDelete INTEGER,
                    cinEnable INTEGER,
	            cinId  INTEGER,
                    cinIpAddress  IpAddress,
                    cinIpv6Address InetAddressIPv6
                    }

             cinIndex  OBJECT-TYPE
	            SYNTAX  INTEGER
		    ACCESS  read-only
		    STATUS  mandatory
		    DESCRIPTION
		    "Chassis Internal Network (CIN) table index."
	            ::= { cinEntry 1 }

	     cinDefExists  OBJECT-TYPE
                    SYNTAX  INTEGER {
                      false(0),
                      true(1)
                    }
                    ACCESS  read-only
                    STATUS  mandatory
                    DESCRIPTION
                    "Indicates if a Chassis Internal Network (CIN) definition exists for
		    this index or not."
                    ::= { cinEntry 2 }

	     cinDelete  OBJECT-TYPE
	            SYNTAX  INTEGER {
		            execute(1)
	            }
	            ACCESS  read-write
	            STATUS  mandatory
	            DESCRIPTION
	            "Delete Chassis Internal Network (CIN) definition.
                     Works like CIN entry disabled. However, the entry is also deleted.

                    NOTE: Value returned for the GET command is meaningless for this
                    MIB object. Deleting a non-defined entry does nothing."
	            ::= { cinEntry 3 }

	     cinEnable  OBJECT-TYPE
	            SYNTAX  INTEGER {
		      disabled(0),
		      enabled(1)
		    }
		    ACCESS  read-write
		    STATUS  mandatory
		    DESCRIPTION
		    "Disable or enable a Chassis Internal Network (CIN) definition.
                       Enabled:
                         MM reads the entry and creates a new CIN interface if the CIN VLAN
                         ID is new and does not have a CIN interface created yet, adds host
                         route, and monitors communication path. Start ARP monitoring if
                         IP is 0.0.0.0.

                        Disabled:
                          Delete host route. If this is the last IP address that uses the CIN
                          interface,
                            - Stop ARP monitoring if IP is 0.0.0.0.
                            - Delete the CIN interface if there is no other entry depends on it."
		    ::= { cinEntry 4 }

	     cinId  OBJECT-TYPE
	            SYNTAX  INTEGER
		    ACCESS  read-write
		    STATUS  mandatory
		    DESCRIPTION
                    "This is the Chassis Internal Network (CIN) Virtual LAN (VLAN) ID for
                    the internal management network between the Management Module,
                    I/O Module, and the blade OS. The range of valid CIN VLAN IDs is
                    3 to 4094 (inclusive). This value cannot be the same as the
                    Serial Over LAN (SOL) or Concurrent KVM (cKVM) VLAN ID.

		    NOTE: If creating a new CIN definition, you must define cinId
		    before you define cinIpAddress.

		    NOTE: Before changing this value on an existing CIN definition,
		    you must first disable the definition."
	            ::= { cinEntry 5 }

	   cinIpAddress    OBJECT-TYPE
                    SYNTAX  IpAddress
                    ACCESS  read-write
                    STATUS  mandatory
                    DESCRIPTION
                    "Chassis Internal Network (CIN) IP address.

		     Restrictions:
                       - CIN entries cannot have matching IP addresses, with the exception of 0.0.0.0.
                       - Multiple IP addresses of 0.0.0.0 with different VLAN IDs are allowed.
                       - The IP address cannot be multi-cast.
                       - The IP address cannot match the MM IP address.
                       - If the CIN IP address is 0.0.0.0, the blade IP address for CIN which is configured
                         in the blade's OS can not be in the same subnet as that of MM.

		    NOTE: If creating a new CIN definition, you must define cinId
		    before you define cinIpAddress.

                    NOTE: Before changing this value on an existing CIN definition,
                    you must first disable the definition.
                    NOTE: When ipv6 is enable on one interface, this column will
                    display all zero IPv4 address"
                    ::= { cinEntry 6}
         cinIpv6Address   OBJECT-TYPE
                        SYNTAX  InetAddressIPv6
                        ACCESS  read-write
                        STATUS  mandatory
                        DESCRIPTION
                        "Chassis Internal Network (CIN) IPv6 address

                        NOTE: When ipv4 is enable on one interface,this column will display
                        all zero IPv6 address."
                        ::= { cinEntry 7}

          -- CIN Status Table

	  cinStatus  OBJECT IDENTIFIER ::= { chassisInternalNetwork 4 }

            cinStatusTable  OBJECT-TYPE
                    SYNTAX  SEQUENCE OF CinStatusEntry
                    ACCESS  not-accessible
                    STATUS  mandatory
                    DESCRIPTION
                    "Table of Chassis Internal Network (CIN) status entry information."
                    ::= { cinStatus 1 }

            cinStatusEntry OBJECT-TYPE
                    SYNTAX CinStatusEntry
                    ACCESS  not-accessible
                    STATUS  mandatory
                    DESCRIPTION
                    "Chassis Internal Network (CIN) status table entry."
                    INDEX { cinStatusIndex }
                    ::= { cinStatusTable 1 }

            CinStatusEntry ::= SEQUENCE {
                    cinStatusIndex  INTEGER,
		    cinStatusString OCTET STRING
                    }

            cinStatusIndex  OBJECT-TYPE
                    SYNTAX  INTEGER
                    ACCESS  read-only
                    STATUS  mandatory
                    DESCRIPTION
                    "The Chassis Internal Network (CIN) status log index number.
                    For consistent results, view as a table and not as individual entries."
                    ::= { cinStatusEntry 1 }

            cinStatusString  OBJECT-TYPE
	            SYNTAX  OCTET STRING
	            ACCESS  read-only
	            STATUS  mandatory
	            DESCRIPTION
		    "Status of a Chassis Internal Network (CIN) connection. For example:

		    Index:1 VLANID:4094 IPADDR:192.168.70.100 MAC:01:0A:0B:00:01:01 Type:Learned Status:Operational

		    Index is the status entry number in the status table. Followed by the
                    VLAN ID, IP address, and MAC address that the Management Module is
		    communicating with on the CIN connection.

		    Type is either 'Configured' or 'Learned'. Learned implies that the
		    Management Module dynamically discovered the IP address.
		    Configured means that the address was explicitly configured in
		    the Management Module.

		    Status can be 'Operational', 'Not Operational', or 'Disabled'.

                    'Operational' means the Management Module can ping the CIN IP address.

		    'Not Operational' means that the Management Module cannot ping the CIN
		    IP address. Verify that the blade and I/O Module are configured properly
		    and that their configurations are compatible with the Management Module.
		    The blade OS also needs to have an IP host route defined
		    (e.g. route add -host 192.168.70.100 eth0.4094).
		    I/O Modules need to have a VLAN defined containing the blade's and the
		    MM's port. Blade and I/O Modules need to be powered up and operational.

                    'Disabled' means that the CIN configuration has been disabled by a
		    Management Module administrator.

                    For consistent results, view as a table and not as individual entries."
                    ::= { cinStatusEntry 2 }

  --  ********************************************************************************
  --  Restart Control
  --  ********************************************************************************

      restartSPImmediately   OBJECT-TYPE
                     SYNTAX  INTEGER {
                      execute(1)
                     }
                     ACCESS  read-write
                     STATUS  mandatory
                     DESCRIPTION
                     "Restart the MM immediately.

                     NOTE: Value returned for the GET command is meaningless for
                     this MIB object."
                     ::= { restartReset 4 }

     restartStandbyMM  OBJECT-TYPE
                    SYNTAX  INTEGER {
                      execute(1)
                     }
                    ACCESS  read-write
                    STATUS  mandatory
                    DESCRIPTION
                    "Restarts the Standby MM from the Primary MM.

                    NOTE: Value returned for the GET command is meaningless for
                    this MIB object.

                    NOTE: This mib object is only applicable to systems with a standby MM."
                    ::= { restartReset 5}

      switchOverRedundantMM  OBJECT-TYPE
                     SYNTAX  INTEGER {
                      execute(1)
                     }
                     ACCESS  read-write
                     STATUS  mandatory
                     DESCRIPTION
                     "Switch over to the redundant Management Module.
                     The failover will not occur if the standby or primary MM is in flashing mode.

                     NOTE: Value returned for the GET command is meaningless for
                     this MIB object.

                     NOTE: This mib object is only applicable to systems with a redundant MM."
                     ::= { restartReset 7 }

      resetSPConfigAndRestart  OBJECT-TYPE
                    SYNTAX  INTEGER {
                      execute(1)
                     }
                    ACCESS  read-write
                    STATUS  mandatory
                    DESCRIPTION
                    "Will cause all the MM information to be reset to it's
                    initial factory defaults (all previous configuration
                    information is lost) and the MM will be re-started.

                    NOTE: Value returned for the GET command is meaningless
                    for this MIB object."
                    ::= { restartReset 20 }

      resetSPConfigAndRestartSaveLogs  OBJECT-TYPE
                    SYNTAX  INTEGER {
                      execute(1)
                     }
                    ACCESS  read-write
                    STATUS  mandatory
                    DESCRIPTION
                    "Will cause all the MM information to be reset to it's
                    initial factory defaults (all previous configuration
                    information is lost) and the MM will be re-started. The
                    logs will be saved.

                    NOTE: Value returned for the GET command is meaningless
                    for this MIB object."
                    ::= { restartReset 21 }

      resetSPConfigAndRestartKeepIP  OBJECT-TYPE
                    SYNTAX  INTEGER {
                      execute(1)
                     }
                    ACCESS  read-write
                    STATUS  mandatory
                    DESCRIPTION
                    "Will cause all the MM information to be reset to it's
                    initial factory defaults (all previous configuration
                    information is lost) and the MM will be re-started. The
                    IP configuration will be saved.

                    NOTE: Value returned for the GET command is meaningless
                    for this MIB object."
                    ::= { restartReset 22 }

      resetSPConfigAndRestartSaveLogsKeepIP  OBJECT-TYPE
                    SYNTAX  INTEGER {
                      execute(1)
                     }
                    ACCESS  read-write
                    STATUS  mandatory
                    DESCRIPTION
                    "Will cause all the MM information to be reset to it's
                    initial factory defaults (all previous configuration
                    information is lost) and the MM will be re-started. The
                    logs and the IP configuration will be saved.

                    NOTE: Value returned for the GET command is meaningless
                    for this MIB object."
                    ::= { restartReset 23 }

  --  ********************************************************************************
  --  processorBlade
  --  ********************************************************************************
    -- This group of objects provides information specific to blades
    processorBlade OBJECT IDENTIFIER ::= { components 1 }

      -- ********************************************************************************
      -- Blade policy control
      -- ********************************************************************************
      bladePolicyControl OBJECT IDENTIFIER ::= { processorBlade 4 }

        bladePolicyControlTable OBJECT-TYPE
                       SYNTAX  SEQUENCE OF BladePolicyControlEntry
                       ACCESS  not-accessible
                       STATUS  mandatory
                       DESCRIPTION
                       "Table of blade power policy control information.
                       Contains power on/off enablement status for each blade."
                       ::= { bladePolicyControl 1 }

         bladePolicyControlEntry OBJECT-TYPE
                       SYNTAX BladePolicyControlEntry
                       ACCESS  not-accessible
                       STATUS  mandatory
                       DESCRIPTION
                       "Power policy control entry"
                       INDEX { policyControlIndex }
                       ::= { bladePolicyControlTable 1 }

         BladePolicyControlEntry ::= SEQUENCE {
                     policyControlIndex INTEGER,
                     policyControlBladeId INTEGER,
                     policyControlBladeExists INTEGER,
                     policyControlBladePowerState INTEGER,
                     policyControlBladeHealthState INTEGER,
                     policyControlBladeName OCTET STRING,
                     policyLocalPowerControlEnable INTEGER,
                     policyWakeOnLanControlEnable INTEGER
         }

         policyControlIndex  OBJECT-TYPE
                     SYNTAX  INTEGER
                     ACCESS  read-only
                     STATUS  mandatory
                     DESCRIPTION
                     "Blade power policy control index."
                     ::= { bladePolicyControlEntry 1 }

         policyControlBladeId  OBJECT-TYPE
                     SYNTAX  INTEGER {
                       blade1(1),
                       blade2(2),
                       blade3(3),
                       blade4(4),
                       blade5(5),
                       blade6(6),
                       blade7(7),
                       blade8(8),
                       blade9(9),
                       blade10(10),
                       blade11(11),
                       blade12(12),
                       blade13(13),
                       blade14(14)
                     }
                     ACCESS  read-only
                     STATUS  mandatory
                     DESCRIPTION
                     "The numeric blade ID."
                     ::= { bladePolicyControlEntry 2 }

         policyControlBladeExists OBJECT-TYPE
                     SYNTAX  INTEGER {
                       false(0),
                       true(1)
                     }
                     ACCESS  read-only
                     STATUS  mandatory
                     DESCRIPTION
                     "Indicates whether the server blade specified exists or not."
                     ::= { bladePolicyControlEntry 3 }

         policyControlBladePowerState OBJECT-TYPE
                     SYNTAX  INTEGER {
                       off(0),
                       on(1),
                       standby(3),
                       hibernate(4),
                       unknown(255)
                     }
                     ACCESS  read-only
                     STATUS  mandatory
                     DESCRIPTION
                     "The power state for blade.
                     0 = off, 1 = on, 3 = standby, 4 = hibernate, 255 = unknown."
                     ::= { bladePolicyControlEntry 4 }

         policyControlBladeHealthState  OBJECT-TYPE
                   SYNTAX  INTEGER {
                     unknown(0),
                     good(1),
                     warning(2),
                     critical(3),
                     kernelMode(4),
                     discovering(5),
                     commError(6),
                     noPower(7),
                     flashing(8),
                     initFailure(9),
                     insufficientPower(10),
                     powerDenied(11),
                     maintMode(12),
                     firehoseDump(13)
                   }
                   ACCESS  read-only
                   STATUS  mandatory
                   DESCRIPTION
                   "The system health state for the blade.

                    Unknown: Blade is in an undefined state.
                    Good: Blade is operating normally.
                    Warning: One or more outstanding warnings exist for this blade.
                    Critical: One or more outstanding critical events for this blade.
                    Kernel Mode: Blade is in kernel mode.
                    Discovering: The MM is currently in the process of discovering this blade.
                    Communications Error: The MM failed to communicate with this blade.
                    No Power: No power to the blade's domain.
                    Flashing: Flashing in progress.
                    Initialization Failure: Blade failed to initialized.
                    Insufficient Power: Not enough power is left in the blade's domain to power the blade.
                    Power Denied: Power was denied to the blade."
                   ::= { bladePolicyControlEntry 5 }

         policyControlBladeName OBJECT-TYPE
                     SYNTAX  OCTET STRING
                     ACCESS  read-only
                     STATUS  mandatory
                     DESCRIPTION
                     "The name of the blade as a null terminated string."
                     ::= { bladePolicyControlEntry 6 }

         policyLocalPowerControlEnable OBJECT-TYPE
                     SYNTAX  INTEGER {
                       disabled(0),
                       enabled(1),
                       notApplicable(255)
                     }
                     ACCESS  read-write
                     STATUS  mandatory
                     DESCRIPTION
                     "Blade local power policy control enablement status."
                     ::= { bladePolicyControlEntry 7 }
                     
         policyWakeOnLanControlEnable OBJECT-TYPE
                     SYNTAX  INTEGER {
                       disabled(0),
                       enabled(1),
                       notApplicable(255)
                     }
                     ACCESS  read-write
                     STATUS  mandatory
                     DESCRIPTION
                     "Blade Wake On LAN enablement status.
                     If WOL is not supported by the blade, it displays 'notApplicable'
                     and WOL can not be enabled or disabled."
                     ::= { bladePolicyControlEntry 10 }

       bladePolicy  OBJECT IDENTIFIER ::= { bladePolicyControl 2}
       -- global blade control policy

         bladePolicyLocalPowerControlEnable OBJECT-TYPE
                     SYNTAX  INTEGER {
                       disabled(0),
                       enabled(1)
                     }
                     ACCESS  read-write
                     STATUS  mandatory
                     DESCRIPTION
                     "Blade local power control enablement status policy."
                     ::= { bladePolicy 1 }
                     
         bladePolicyWakeOnLanControlEnable OBJECT-TYPE
                     SYNTAX  INTEGER {
                       disabled(0),
                       enabled(1),
                       notApplicable(255)
                     }
                     ACCESS  read-write
                     STATUS  mandatory
                     DESCRIPTION
                     "Blade Wake On LAN enablement status policy. The
                      notApplicable(255) enumeration is not valid for SET

                      operations.

                     NOTE: Value returned for the GET command is meaningless
                     for this MIB object."
                     ::= { bladePolicy 4 }

      -- ********************************************************************************
      -- Blade system health state params
      -- ********************************************************************************

      bladeMonitors OBJECT IDENTIFIER ::= { processorBlade 5 }

       bladeSystemStatusTable OBJECT-TYPE
                     SYNTAX  SEQUENCE OF BladeSystemStatusEntry
                     ACCESS  not-accessible
                     STATUS  mandatory
                     DESCRIPTION
                     "Table of blade status information."
                     ::= { bladeMonitors 1 }

       bladeSystemStatusEntry OBJECT-TYPE
                     SYNTAX BladeSystemStatusEntry
                     ACCESS  not-accessible
                     STATUS  mandatory
                     DESCRIPTION
                     "Blade system status entry"
                     INDEX { bladeStatusIndex }
                     ::= { bladeSystemStatusTable 1 }

       BladeSystemStatusEntry ::= SEQUENCE {
                   bladeStatusIndex INTEGER,
                   bladeId INTEGER,
                   bladeExists INTEGER,
                   bladePowerState INTEGER,
                   bladeHealthState INTEGER,
                   bladeName OCTET STRING,
                   bladeRemotePowerEnable INTEGER,
                   bladeConnectionType INTEGER,
                   bladeRemoteWakeOnLanEnable INTEGER,
                   bladeServerExpansion INTEGER,
                   bladeWidth INTEGER,
                   bladeServerExpansion2 INTEGER,
                   bladeConnectionType2 INTEGER,
                   bladeConnectionType3 INTEGER,
                   bladeConnectionType4 INTEGER,
                   bladeConnectionType5 INTEGER,
                   bladeHighSpeedConnectionType INTEGER,
                   bladeIOCompatibility OCTET STRING,
                   bladeInventoryReady INTEGER
                   }


       bladeStatusIndex OBJECT-TYPE
                   SYNTAX  INTEGER
                   ACCESS  read-only
                   STATUS  mandatory
                   DESCRIPTION
                   "Blade system status index."
                   ::= { bladeSystemStatusEntry 1 }

       bladeId OBJECT-TYPE
                   SYNTAX  INTEGER {
                       blade1(1),
                       blade2(2),
                       blade3(3),
                       blade4(4),
                       blade5(5),
                       blade6(6),
                       blade7(7),
                       blade8(8),
                       blade9(9),
                       blade10(10),
                       blade11(11),
                       blade12(12),
                       blade13(13),
                       blade14(14)
                     }
                   ACCESS  read-only
                   STATUS  mandatory
                   DESCRIPTION
                   "The numeric blade ID."
                   ::= { bladeSystemStatusEntry 2 }

       bladeExists OBJECT-TYPE
                   SYNTAX  INTEGER {
                     false(0),
                     true(1)
                   }
                   ACCESS  read-only
                   STATUS  mandatory
                   DESCRIPTION
                   "Indicates whether the server blade specified exists or not."
                   ::= { bladeSystemStatusEntry 3 }

       bladePowerState  OBJECT-TYPE
                   SYNTAX  INTEGER {
                     off(0),
                     on(1),
                     standby(3),
                     hibernate(4),
                     unknown(255)
                   }
                   ACCESS  read-only
                   STATUS  mandatory
                   DESCRIPTION
                   "Indicates the power state of the blade specified."
                   ::= { bladeSystemStatusEntry 4 }

       bladeHealthState  OBJECT-TYPE
                   SYNTAX  INTEGER {
                     unknown(0),
                     good(1),
                     warning(2),
                     critical(3),
                     kernelMode(4),
                     discovering(5),
                     commError(6),
                     noPower(7),
                     flashing(8),
                     initFailure(9),
                     insufficientPower(10),
                     powerDenied(11),
                     maintMode(12),
                     firehoseDump(13)
                   }
                   ACCESS  read-only
                   STATUS  mandatory
                   DESCRIPTION
                   "The system health state for the blade.

                    Unknown: Blade is in an undefined state.
                    Good: Blade is operating normally.
                    Warning: One or more outstanding warnings exist for this blade.
                    Critical: One or more outstanding critical events for this blade.
                    Kernel Mode: Blade is in kernel mode.
                    Discovering: The MM is currently in the process of discovering this blade.
                    Communications Error: The MM failed to communicate with this blade.
                    No Power: No power to the blade's domain.
                    Flashing: Flashing in progress.
                    Initialization Failure: Blade failed to initialized.
                    Insufficient Power: Not enough power is left in the blade's domain to power the blade.
                    Power Denied: Power was denied to the blade."
                   ::= { bladeSystemStatusEntry 5 }

       bladeName OBJECT-TYPE
                   SYNTAX  OCTET STRING
                   ACCESS  read-only
                   STATUS  mandatory
                   DESCRIPTION
                   "The name of the blade as a null terminated string."
                   ::= { bladeSystemStatusEntry 6 }

       bladeRemotePowerEnable  OBJECT-TYPE
                   SYNTAX  INTEGER {
                     disabled(0),
                     enabled(1)
                   }
                   ACCESS  read-only
                   STATUS  mandatory
                   DESCRIPTION
                   "Remote power state for the blade."
                   ::= { bladeSystemStatusEntry 7 }

       bladeConnectionType  OBJECT-TYPE
                   SYNTAX  INTEGER {
                     none(0),
                     ethernet(1),
                     fiber(2),
                     serial(3),
                     opticalPassThrough(4),
                     infiniband(5),
                     iSCSI(6)
                   }
                   ACCESS  read-only
                   STATUS  mandatory
                   DESCRIPTION
                   "Connection type of the expansion card number one."
                   ::= { bladeSystemStatusEntry 10 }

       bladeRemoteWakeOnLanEnable  OBJECT-TYPE
                   SYNTAX  INTEGER {
                     disabled(0),
                     enabled(1),
                     notApplicable(255)
                   }
                   ACCESS  read-only
                   STATUS  mandatory
                   DESCRIPTION
                   "Remote wake on LAN state for the blade."
                   ::= { bladeSystemStatusEntry 13 }

       bladeServerExpansion  OBJECT-TYPE
                   SYNTAX  INTEGER {
                     no(0),
                     yes(1)
                   }
                   ACCESS  read-only
                   STATUS  mandatory
                   DESCRIPTION
                   "This shows whether this blade has an expansion board attached.
                   A yes column indicates that an expansion board is installed for this
                   blade."
                   ::= { bladeSystemStatusEntry 14 }

       bladeWidth  OBJECT-TYPE
                   SYNTAX  INTEGER
                   ACCESS  read-only
                   STATUS  mandatory
                   DESCRIPTION
                   "The width of the blade including any supplement blade attached to it"
                   ::= { bladeSystemStatusEntry 15 }

       bladeServerExpansion2  OBJECT-TYPE
                   SYNTAX  INTEGER {
                     no(0),
                     yes(1)
                   }
                   ACCESS  read-only
                   STATUS  mandatory
                   DESCRIPTION
                   "This shows whether this blade has an expansion board attached.
                   A yes column indicates that an expansion board is installed for this
                   blade."
                   ::= { bladeSystemStatusEntry 17 }

       bladeConnectionType2  OBJECT-TYPE
                   SYNTAX  INTEGER {
                     none(0),
                     ethernet(1),
                     fiber(2),
                     serial(3),
                     opticalPassThrough(4),
                     infiniband(5),
                     iSCSI(6)
                   }
                   ACCESS  read-only
                   STATUS  mandatory
                   DESCRIPTION
                   "Connection type of the expansion card number 2."
                   ::= { bladeSystemStatusEntry 22 }

       bladeConnectionType3  OBJECT-TYPE
                   SYNTAX  INTEGER {
                     none(0),
                     ethernet(1),
                     fiber(2),
                     serial(3),
                     opticalPassThrough(4),
                     infiniband(5),
                     iSCSI(6)
                   }
                   ACCESS  read-only
                   STATUS  mandatory
                   DESCRIPTION
                   "Connection type of the expansion card number 3."
                   ::= { bladeSystemStatusEntry 23 }

       bladeConnectionType4  OBJECT-TYPE
                   SYNTAX  INTEGER {
                     none(0),
                     ethernet(1),
                     fiber(2),
                     serial(3),
                     opticalPassThrough(4),
                     infiniband(5),
                     iSCSI(6)
                   }
                   ACCESS  read-only
                   STATUS  mandatory
                   DESCRIPTION
                   "Connection type of the expansion card number 4."
                   ::= { bladeSystemStatusEntry 24 }

       bladeConnectionType5  OBJECT-TYPE
                   SYNTAX  INTEGER {
                     none(0),
                     ethernet(1),
                     fiber(2),
                     serial(3),
                     opticalPassThrough(4),
                     infiniband(5),
                     iSCSI(6)
                   }
                   ACCESS  read-only
                   STATUS  mandatory
                   DESCRIPTION
                   "Connection type of the expansion card number 5."
                   ::= { bladeSystemStatusEntry 25 }

       bladeHighSpeedConnectionType OBJECT-TYPE
                   SYNTAX  INTEGER {
                     none(0),
                     ethernet(1),
                     fiber(2),
                     serial(3),
                     opticalPassThrough(4),
                     infiniband(5),
                     iSCSI(6),
                     infinibandPassThrough(7)
                   }
                   ACCESS  read-only
                   STATUS  mandatory
                   DESCRIPTION
                   "Connection type of the high speed expansion card number 1."
                   ::= { bladeSystemStatusEntry 41 }

       bladeIOCompatibility OBJECT-TYPE
                   SYNTAX  OCTET STRING
                   ACCESS  read-only
                   STATUS  mandatory
                   DESCRIPTION
                   "I/O compatibility status for the blade. This reflects the 
                   worst-case status of this blades network adapter connections  
                   to all of the switches in the chassis. For example, if this 
                   blade has 4 network connections to the four IOMs in the chassis
                   and three are OK, but one indicates Attention, then this 
                   MIB object will indicate Attention. 

                   For an equivalent view using the web, visit the 
                   Chassis Management->Compute Nodes menu item and for a given 
                   blade, look at the I/O Compatibility column. Note that this column 
                   is not shown by default, but can be added to the view using the 
                   Columns dropdown to add it to the table.   

                   The possible values and their meanings are as follows:

                   unknown: This indicates a communication error for the blade.

                   ok: This is the normal (good) case where the blade and the
                       corresponding I/O modules it is internally wired to have no
                       compatibility issues.

                   noIOMs: This means there are no I/O modules in any of the
                           corresponding I/O module bays this blade is internally wired to.

                   attention: This indicates that one or more of the corresponding
                              I/O modules are in communication error.

                   mismatch: This indicates one of the following cases:
                             Fabric types are incompatible
                             An unknown I/O module type
                             An unknown fabric type on the blade"

                   ::= { bladeSystemStatusEntry 51 }

       bladeInventoryReady OBJECT-TYPE
                   SYNTAX  INTEGER {
                     notReady(0),
                     ready(1)
                   }
                   ACCESS  read-only
                   STATUS  mandatory
                   DESCRIPTION
                   "When a blade management controller or the MM is reset, the 
                    blade inventory data is refreshed in the MM database. This includes
                    items like VPD (e.g. - serial number, UUID) and MAC address information.
                    
                    Applications need to know when this information has been populated on the MM
                    before they begin to query it using SNMP or other means. This simple flag 
                    object will return a ready or notReady indication for each blade regarding the 
                    status of this information. 
                    
                    Notes:
                     
                    For blades that are experiencing a 'communication failure' or 
                    'initialization failure' condition, this object will continue to indicate 
                    notReady until the condition is resolved. Therefore, any application that 
                    polls this object should also incorporate a timeout period."
                   ::= { bladeSystemStatusEntry 52 }

      bladeHealthSummaryTable OBJECT-TYPE
                    SYNTAX  SEQUENCE OF BladeHealthSummaryEntry
                    ACCESS  not-accessible
                    STATUS  mandatory
                    DESCRIPTION
                    "Table of blade health summary information.
                    Contains information about the overall blade health status."
                    ::= { bladeMonitors 2 }

      bladeHealthSummaryEntry OBJECT-TYPE
                    SYNTAX BladeHealthSummaryEntry
                    ACCESS  not-accessible
                    STATUS  mandatory
                    DESCRIPTION
                    "Blade health summary entry"
                    INDEX { bladeHealthSummaryIndex }
                    ::= { bladeHealthSummaryTable 1 }

      BladeHealthSummaryEntry ::= SEQUENCE {
                  bladeHealthSummaryIndex INTEGER,
                  bladeHealthSummaryBladeId INTEGER,
                  bladeHealthSummarySeverity OCTET STRING,
                  bladeHealthSummaryDescription OCTET STRING,
                  bladeHealthSummaryDateTime OCTET STRING,
                  bladeHealthSummaryEventID OCTET STRING
                  }

      bladeHealthSummaryIndex  OBJECT-TYPE
                  SYNTAX  INTEGER
                  ACCESS  read-only
                  STATUS  mandatory
                  DESCRIPTION
                  "Blade health summary index."
                  ::= { bladeHealthSummaryEntry 1 }

       bladeHealthSummaryBladeId OBJECT-TYPE
                   SYNTAX  INTEGER {
                       blade1(1),
                       blade2(2),
                       blade3(3),
                       blade4(4),
                       blade5(5),
                       blade6(6),
                       blade7(7),
                       blade8(8),
                       blade9(9),
                       blade10(10),
                       blade11(11),
                       blade12(12),
                       blade13(13),
                       blade14(14)
                     }
                   ACCESS  read-only
                   STATUS  mandatory
                   DESCRIPTION
                   "The numeric blade ID."
                   ::= { bladeHealthSummaryEntry 2 }

      bladeHealthSummarySeverity  OBJECT-TYPE
                  SYNTAX  OCTET STRING
                  ACCESS  read-only
                  STATUS  mandatory
                  DESCRIPTION
                  "System health summary severity."
                  ::= { bladeHealthSummaryEntry 3 }

      bladeHealthSummaryDescription  OBJECT-TYPE
                  SYNTAX  OCTET STRING
                  ACCESS  read-only
                  STATUS  mandatory
                  DESCRIPTION
                  "System health summary description.(Deprecated)"
                  ::= { bladeHealthSummaryEntry 4 }

      bladeHealthSummaryDateTime  OBJECT-TYPE
                  SYNTAX  OCTET STRING
                  ACCESS  read-only
                  STATUS  mandatory
                  DESCRIPTION
                  "System health summary date time.(Deprecated)"
                  ::= { bladeHealthSummaryEntry 5 }

      bladeHealthSummaryEventID  OBJECT-TYPE
                  SYNTAX  OCTET STRING
                  ACCESS  read-only
                  STATUS  mandatory
                  DESCRIPTION
                  "System health summary event ID.(Deprecated)"
                  ::= { bladeHealthSummaryEntry 6 }

      bladeTemperaturesTable OBJECT-TYPE
                     SYNTAX  SEQUENCE OF BladeTemperaturesEntry
                     ACCESS  not-accessible
                     STATUS  mandatory
                     DESCRIPTION
                     "Table of blade temperatures information."
                     ::= { bladeMonitors 3 }

       bladeTemperaturesEntry OBJECT-TYPE
                     SYNTAX BladeTemperaturesEntry
                     ACCESS  not-accessible
                     STATUS  mandatory
                     DESCRIPTION
                     "Blade temperatures table entry"
                     INDEX { temperatureIndex }
                     ::= { bladeTemperaturesTable 1 }

       BladeTemperaturesEntry ::= SEQUENCE {
                   temperatureIndex INTEGER,
                   temperatureBladeId INTEGER,
                   temperatureBladeExists INTEGER,
                   temperatureBladePowerState INTEGER,
                   temperatureBladeName OCTET STRING,
                   temperatureCPU1 OCTET STRING,
                   temperatureCPU2 OCTET STRING,
                   temperatureCPU3 OCTET STRING,
                   temperatureCPU4 OCTET STRING,
                   temperatureDASD1 OCTET STRING,
                   bladeSensorTempCapability INTEGER,
                   bladeSensor1Temp OCTET STRING,
                   bladeSensor2Temp OCTET STRING,
                   bladeSensor3Temp OCTET STRING,
                   bladeSensor4Temp OCTET STRING,
                   bladeSensor5Temp OCTET STRING,
                   bladeSensor6Temp OCTET STRING,
                   bladeSensor7Temp OCTET STRING,
                   bladeSensor8Temp OCTET STRING,
                   bladeSensor9Temp OCTET STRING
                   }

       temperatureIndex  OBJECT-TYPE
                   SYNTAX  INTEGER
                   ACCESS  read-only
                   STATUS  mandatory
                   DESCRIPTION
                   "Blade temperatures table index."
                   ::= { bladeTemperaturesEntry 1 }

       temperatureBladeId  OBJECT-TYPE
                   SYNTAX  INTEGER {
                     blade1(1),
                     blade2(2),
                     blade3(3),
                     blade4(4),
                     blade5(5),
                     blade6(6),
                     blade7(7),
                     blade8(8),
                     blade9(9),
                     blade10(10),
                     blade11(11),
                     blade12(12),
                     blade13(13),
                     blade14(14)
                   }
                   ACCESS  read-only
                   STATUS  mandatory
                   DESCRIPTION
                   "The numeric blade ID."
                   ::= { bladeTemperaturesEntry 2 }

       temperatureBladeExists OBJECT-TYPE
                   SYNTAX  INTEGER {
                     false(0),
                     true(1)
                   }
                   ACCESS  read-only
                   STATUS  mandatory
                   DESCRIPTION
                   "Indicates whether the server blade specified exists or not."
                   ::= { bladeTemperaturesEntry 3 }

       temperatureBladePowerState OBJECT-TYPE
                   SYNTAX  INTEGER {
                     off(0),
                     on(1),
                     standby(3),
                     hibernate(4),
                     unknown(255)
                   }
                   ACCESS  read-only
                   STATUS  mandatory
                   DESCRIPTION
                   "Indicates the power state of the blade specified."
                   ::= { bladeTemperaturesEntry 4 }

       temperatureBladeName OBJECT-TYPE
                   SYNTAX  OCTET STRING
                   ACCESS  read-only
                   STATUS  mandatory
                   DESCRIPTION
                   "The name of the blade as a null terminated string."
                   ::= { bladeTemperaturesEntry 5 }

       temperatureCPU1 OBJECT-TYPE
                   SYNTAX  OCTET STRING
                   ACCESS  read-only
                   STATUS  mandatory
                   DESCRIPTION
                   "The blade CPU temperature in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperaturesEntry 6 }

       temperatureCPU2 OBJECT-TYPE
                   SYNTAX  OCTET STRING
                   ACCESS  read-only
                   STATUS  mandatory
                   DESCRIPTION
                   "The blade CPU temperature in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperaturesEntry 7 }

       temperatureCPU3 OBJECT-TYPE
                   SYNTAX  OCTET STRING
                   ACCESS  read-only
                   STATUS  mandatory
                   DESCRIPTION
                   "The blade CPU temperature in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperaturesEntry 8 }

       temperatureCPU4 OBJECT-TYPE
                   SYNTAX  OCTET STRING
                   ACCESS  read-only
                   STATUS  mandatory
                   DESCRIPTION
                   "The blade CPU temperature in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperaturesEntry 9 }

       temperatureDASD1 OBJECT-TYPE
                   SYNTAX  OCTET STRING
                   ACCESS  read-only
                   STATUS  mandatory
                   DESCRIPTION
                   "The blade DASD temperature in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperaturesEntry 10 }

       bladeSensorTempCapability OBJECT-TYPE
                   SYNTAX  INTEGER {
                     false(0),
                     true(1)
                   }
                   ACCESS  read-only
                   STATUS  mandatory
                   DESCRIPTION
                   "Indicates whether the server blade is IPMI capable or not."
                   ::= { bladeTemperaturesEntry 11 }

       bladeSensor1Temp OBJECT-TYPE
                   SYNTAX  OCTET STRING
                   ACCESS  read-only
                   STATUS  mandatory
                   DESCRIPTION
                   "Temperature reading for an IPMI blade expressed in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperaturesEntry 12 }

       bladeSensor2Temp OBJECT-TYPE
                   SYNTAX  OCTET STRING
                   ACCESS  read-only
                   STATUS  mandatory
                   DESCRIPTION
                   "Temperature reading for an IPMI blade expressed in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperaturesEntry 13 }

       bladeSensor3Temp OBJECT-TYPE
                   SYNTAX  OCTET STRING
                   ACCESS  read-only
                   STATUS  mandatory
                   DESCRIPTION
                   "Temperature reading for an IPMI blade expressed in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperaturesEntry 14 }

       bladeSensor4Temp OBJECT-TYPE
                   SYNTAX  OCTET STRING
                   ACCESS  read-only
                   STATUS  mandatory
                   DESCRIPTION
                   "Temperature reading for an IPMI blade expressed in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperaturesEntry 15 }

       bladeSensor5Temp OBJECT-TYPE
                   SYNTAX  OCTET STRING
                   ACCESS  read-only
                   STATUS  mandatory
                   DESCRIPTION
                   "Temperature reading for an IPMI blade expressed in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperaturesEntry 16 }

       bladeSensor6Temp OBJECT-TYPE
                   SYNTAX  OCTET STRING
                   ACCESS  read-only
                   STATUS  mandatory
                   DESCRIPTION
                   "Temperature reading for an IPMI blade expressed in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperaturesEntry 17 }

       bladeSensor7Temp OBJECT-TYPE
                   SYNTAX  OCTET STRING
                   ACCESS  read-only
                   STATUS  mandatory
                   DESCRIPTION
                   "Temperature reading for an IPMI blade expressed in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperaturesEntry 18 }

       bladeSensor8Temp OBJECT-TYPE
                   SYNTAX  OCTET STRING
                   ACCESS  read-only
                   STATUS  mandatory
                   DESCRIPTION
                   "Temperature reading for an IPMI blade expressed in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperaturesEntry 19 }

        bladeSensor9Temp OBJECT-TYPE
                   SYNTAX  OCTET STRING
                   ACCESS  read-only
                   STATUS  mandatory
                   DESCRIPTION
                   "Temperature reading for an IPMI blade expressed in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperaturesEntry 20 }

      bladeTemperatureThresholdsTable OBJECT-TYPE
                     SYNTAX  SEQUENCE OF BladeTemperatureThresholdsEntry
                     ACCESS  not-accessible
                     STATUS  mandatory
                     DESCRIPTION
                     "Table of blade temperature thresholds information."
                     ::= { bladeMonitors 4 }

       bladeTemperatureThresholdsEntry OBJECT-TYPE
                     SYNTAX BladeTemperatureThresholdsEntry
                     ACCESS  not-accessible
                     STATUS  mandatory
                     DESCRIPTION
                     "Blade temperature thresholds table entry"
                     INDEX { temperatureThresholdIndex }
                     ::= { bladeTemperatureThresholdsTable 1 }

       BladeTemperatureThresholdsEntry ::= SEQUENCE {
                   temperatureThresholdIndex INTEGER,
                   temperatureThresholdBladeId INTEGER,
                   temperatureThresholdBladeExists INTEGER,
                   temperatureThresholdBladePowerState INTEGER,
                   temperatureThresholdBladeName OCTET STRING,
                   temperatureCPU1HardShutdown OCTET STRING,
                   temperatureCPU1Warning OCTET STRING,
                   temperatureCPU1WarningReset OCTET STRING,
                   temperatureCPU2HardShutdown OCTET STRING,
                   temperatureCPU2Warning OCTET STRING,
                   temperatureCPU2WarningReset OCTET STRING,
                   temperatureCPU3HardShutdown OCTET STRING,
                   temperatureCPU3Warning OCTET STRING,
                   temperatureCPU3WarningReset OCTET STRING,
                   temperatureCPU4HardShutdown OCTET STRING,
                   temperatureCPU4Warning OCTET STRING,
                   temperatureCPU4WarningReset OCTET STRING,
                   temperatureDASD1HardShutdown OCTET STRING,
                   temperatureDASD1Warning OCTET STRING,
                   temperatureDASD1WarningReset OCTET STRING,
                   bladeTempThresholdSensorCapability INTEGER,
                   temperatureSensor1HardShutdown OCTET STRING,
                   temperatureSensor1Warning OCTET STRING,
                   temperatureSensor1WarningReset OCTET STRING,
                   temperatureSensor2HardShutdown OCTET STRING,
                   temperatureSensor2Warning OCTET STRING,
                   temperatureSensor2WarningReset OCTET STRING,
                   temperatureSensor3HardShutdown OCTET STRING,
                   temperatureSensor3Warning OCTET STRING,
                   temperatureSensor3WarningReset OCTET STRING,
                   temperatureSensor4HardShutdown OCTET STRING,
                   temperatureSensor4Warning OCTET STRING,
                   temperatureSensor4WarningReset OCTET STRING,
                   temperatureSensor5HardShutdown OCTET STRING,
                   temperatureSensor5Warning OCTET STRING,
                   temperatureSensor5WarningReset OCTET STRING,
                   temperatureSensor6HardShutdown OCTET STRING,
                   temperatureSensor6Warning OCTET STRING,
                   temperatureSensor6WarningReset OCTET STRING,
                   temperatureSensor7HardShutdown OCTET STRING,
                   temperatureSensor7Warning OCTET STRING,
                   temperatureSensor7WarningReset OCTET STRING,
                   temperatureSensor8HardShutdown OCTET STRING,
                   temperatureSensor8Warning OCTET STRING,
                   temperatureSensor8WarningReset OCTET STRING,
                   temperatureSensor9HardShutdown OCTET STRING,
                   temperatureSensor9Warning OCTET STRING,
                   temperatureSensor9WarningReset OCTET STRING
                   }

       temperatureThresholdIndex  OBJECT-TYPE
                   SYNTAX  INTEGER
                   ACCESS  read-only
                   STATUS  mandatory
                   DESCRIPTION
                   "Blade temperature threshold table index."
                   ::= { bladeTemperatureThresholdsEntry 1 }

       temperatureThresholdBladeId  OBJECT-TYPE
                   SYNTAX  INTEGER {
                     blade1(1),
                     blade2(2),
                     blade3(3),
                     blade4(4),
                     blade5(5),
                     blade6(6),
                     blade7(7),
                     blade8(8),
                     blade9(9),
                     blade10(10),
                     blade11(11),
                     blade12(12),
                     blade13(13),
                     blade14(14)
                   }
                   ACCESS  read-only
                   STATUS  mandatory
                   DESCRIPTION
                   "The numeric blade ID."
                   ::= { bladeTemperatureThresholdsEntry 2 }

       temperatureThresholdBladeExists OBJECT-TYPE
                   SYNTAX  INTEGER {
                     false(0),
                     true(1)
                   }
                   ACCESS  read-only
                   STATUS  mandatory
                   DESCRIPTION
                   "Indicates whether the server blade specified exists or not."
                   ::= { bladeTemperatureThresholdsEntry 3 }

       temperatureThresholdBladePowerState OBJECT-TYPE
                   SYNTAX  INTEGER {
                     off(0),
                     on(1),
                     standby(3),
                     hibernate(4),
                     unknown(255)
                   }
                   ACCESS  read-only
                   STATUS  mandatory
                   DESCRIPTION
                   "Indicates the power state of the blade specified."
                   ::= { bladeTemperatureThresholdsEntry 4 }

       temperatureThresholdBladeName OBJECT-TYPE
                   SYNTAX  OCTET STRING
                   ACCESS  read-only
                   STATUS  mandatory
                   DESCRIPTION
                   "The name of the blade as a null terminated string."
                   ::= { bladeTemperatureThresholdsEntry 5 }

       temperatureCPU1HardShutdown OBJECT-TYPE
                   SYNTAX  OCTET STRING
                   ACCESS  read-only
                   STATUS  mandatory
                   DESCRIPTION
                   "The blade CPU hard shutdown temperature in degrees
                   centigrade(C).  If the component's temperature rises above
                   this value the system will be powered off immediately.
                   If enabled, a critical alert/event will be generated.
                   An octet string expressed as 'sddd.dd Centigrade' where:
                   s is the sign ('-' for negative or blank space for positive)
                   d is a decimal digit or blank space for a leading zero.
                   The string 'Not Readable!' indicates that the given monitor
                   is not supported on this system.
                   The string 'No Temperature' indicates that the given monitor
                   does not exist on this system or is powered off."
                   ::= { bladeTemperatureThresholdsEntry 6 }

       temperatureCPU1Warning OBJECT-TYPE
                   SYNTAX  OCTET STRING
                   ACCESS  read-only
                   STATUS  mandatory
                   DESCRIPTION
                   "The blade CPU warning temperature in degrees centigrade(C).
                   If the temperature rises above this value a warning alert/event
                   if enabled will be generated.
                   An octet string expressed as 'sddd.dd Centigrade' where:
                   s is the sign ('-' for negative or blank space for positive)
                   d is a decimal digit or blank space for a leading zero.
                   The string 'Not Readable!' indicates that the given monitor
                   is not supported on this system.
                   The string 'No Temperature' indicates that the given monitor
                   does not exist on this system or is powered off."
                   ::= { bladeTemperatureThresholdsEntry 7 }

       temperatureCPU1WarningReset OBJECT-TYPE
                   SYNTAX  OCTET STRING
                   ACCESS  read-only
                   STATUS  mandatory
                   DESCRIPTION
                   "The blade CPU warning reset temperature in degrees
                   centigrade(C).  If the temperature rises above this value and
                   if a warning alert/event had previously been created then the
                   alert/event will be reset.
                   An octet string expressed as 'sddd.dd Centigrade' where:
                   s is the sign ('-' for negative or blank space for positive)
                   d is a decimal digit or blank space for a leading zero.
                   The string 'Not Readable!' indicates that the given monitor
                   is not supported on this system.
                   The string 'No Temperature' indicates that the given monitor
                   does not exist on this system or is powered off."
                   ::= { bladeTemperatureThresholdsEntry 8 }

       temperatureCPU2HardShutdown OBJECT-TYPE
                   SYNTAX  OCTET STRING
                   ACCESS  read-only
                   STATUS  mandatory
                   DESCRIPTION
                   "The blade CPU hard shutdown temperature in degrees
                   centigrade(C).  If the component's temperature rises above
                   this value the system will be powered off immediately.
                   If enabled, a critical alert/event will be generated.
                   An octet string expressed as 'sddd.dd Centigrade' where:
                   s is the sign ('-' for negative or blank space for positive)
                   d is a decimal digit or blank space for a leading zero.
                   The string 'Not Readable!' indicates that the given monitor
                   is not supported on this system.
                   The string 'No Temperature' indicates that the given monitor
                   does not exist on this system or is powered off."
                   ::= { bladeTemperatureThresholdsEntry 9 }

       temperatureCPU2Warning OBJECT-TYPE
                   SYNTAX  OCTET STRING
                   ACCESS  read-only
                   STATUS  mandatory
                   DESCRIPTION
                   "The blade CPU warning temperature in degrees centigrade(C).
                   If the temperature rises above this value a warning alert/event
                   if enabled will be generated.
                   An octet string expressed as 'sddd.dd Centigrade' where:
                   s is the sign ('-' for negative or blank space for positive)
                   d is a decimal digit or blank space for a leading zero.
                   The string 'Not Readable!' indicates that the given monitor
                   is not supported on this system.
                   The string 'No Temperature' indicates that the given monitor
                   does not exist on this system or is powered off."
                   ::= { bladeTemperatureThresholdsEntry 10 }

       temperatureCPU2WarningReset OBJECT-TYPE
                   SYNTAX  OCTET STRING
                   ACCESS  read-only
                   STATUS  mandatory
                   DESCRIPTION
                   "The blade CPU warning reset temperature in degrees
                   centigrade(C).  If the temperature rises above this value and
                   if a warning alert/event had previously been created then the
                   alert/event will be reset.
                   An octet string expressed as 'sddd.dd Centigrade' where:
                   s is the sign ('-' for negative or blank space for positive)
                   d is a decimal digit or blank space for a leading zero.
                   The string 'Not Readable!' indicates that the given monitor
                   is not supported on this system.
                   The string 'No Temperature' indicates that the given monitor
                   does not exist on this system or is powered off."
                   ::= { bladeTemperatureThresholdsEntry 11 }

       temperatureCPU3HardShutdown OBJECT-TYPE
                   SYNTAX  OCTET STRING
                   ACCESS  read-only
                   STATUS  mandatory
                   DESCRIPTION
                   "The blade CPU hard shutdown temperature in degrees
                   centigrade(C).  If the component's temperature rises above
                   this value the system will be powered off immediately.
                   If enabled, a critical alert/event will be generated.
                   An octet string expressed as 'sddd.dd Centigrade' where:
                   s is the sign ('-' for negative or blank space for positive)
                   d is a decimal digit or blank space for a leading zero.
                   The string 'Not Readable!' indicates that the given monitor
                   is not supported on this system.
                   The string 'No Temperature' indicates that the given monitor
                   does not exist on this system or is powered off."
                   ::= { bladeTemperatureThresholdsEntry 12 }

       temperatureCPU3Warning OBJECT-TYPE
                   SYNTAX  OCTET STRING
                   ACCESS  read-only
                   STATUS  mandatory
                   DESCRIPTION
                   "The blade CPU warning temperature in degrees centigrade(C).
                   If the temperature rises above this value a warning alert/event
                   if enabled will be generated.
                   An octet string expressed as 'sddd.dd Centigrade' where:
                   s is the sign ('-' for negative or blank space for positive)
                   d is a decimal digit or blank space for a leading zero.
                   The string 'Not Readable!' indicates that the given monitor
                   is not supported on this system.
                   The string 'No Temperature' indicates that the given monitor
                   does not exist on this system or is powered off."
                   ::= { bladeTemperatureThresholdsEntry 13 }

       temperatureCPU3WarningReset OBJECT-TYPE
                   SYNTAX  OCTET STRING
                   ACCESS  read-only
                   STATUS  mandatory
                   DESCRIPTION
                   "The blade CPU warning reset temperature in degrees
                   centigrade(C).  If the temperature rises above this value and
                   if a warning alert/event had previously been created then the
                   alert/event will be reset.
                   An octet string expressed as 'sddd.dd Centigrade' where:
                   s is the sign ('-' for negative or blank space for positive)
                   d is a decimal digit or blank space for a leading zero.
                   The string 'Not Readable!' indicates that the given monitor
                   is not supported on this system.
                   The string 'No Temperature' indicates that the given monitor
                   does not exist on this system or is powered off."
                   ::= { bladeTemperatureThresholdsEntry 14 }

       temperatureCPU4HardShutdown OBJECT-TYPE
                   SYNTAX  OCTET STRING
                   ACCESS  read-only
                   STATUS  mandatory
                   DESCRIPTION
                   "The blade CPU hard shutdown temperature in degrees
                   centigrade(C).  If the component's temperature rises above
                   this value the system will be powered off immediately.
                   If enabled, a critical alert/event will be generated.
                   An octet string expressed as 'sddd.dd Centigrade' where:
                   s is the sign ('-' for negative or blank space for positive)
                   d is a decimal digit or blank space for a leading zero.
                   The string 'Not Readable!' indicates that the given monitor
                   is not supported on this system.
                   The string 'No Temperature' indicates that the given monitor
                   does not exist on this system or is powered off."
                   ::= { bladeTemperatureThresholdsEntry 15 }

       temperatureCPU4Warning OBJECT-TYPE
                   SYNTAX  OCTET STRING
                   ACCESS  read-only
                   STATUS  mandatory
                   DESCRIPTION
                   "The blade CPU warning temperature in degrees centigrade(C).
                   If the temperature rises above this value a warning alert/event
                   if enabled will be generated.
                   An octet string expressed as 'sddd.dd Centigrade' where:
                   s is the sign ('-' for negative or blank space for positive)
                   d is a decimal digit or blank space for a leading zero.
                   The string 'Not Readable!' indicates that the given monitor
                   is not supported on this system.
                   The string 'No Temperature' indicates that the given monitor
                   does not exist on this system or is powered off."
                   ::= { bladeTemperatureThresholdsEntry 16 }

       temperatureCPU4WarningReset OBJECT-TYPE
                   SYNTAX  OCTET STRING
                   ACCESS  read-only
                   STATUS  mandatory
                   DESCRIPTION
                   "The blade CPU warning reset temperature in degrees
                   centigrade(C).  If the temperature rises above this value and
                   if a warning alert/event had previously been created then the
                   alert/event will be reset.
                   An octet string expressed as 'sddd.dd Centigrade' where:
                   s is the sign ('-' for negative or blank space for positive)
                   d is a decimal digit or blank space for a leading zero.
                   The string 'Not Readable!' indicates that the given monitor
                   is not supported on this system.
                   The string 'No Temperature' indicates that the given monitor
                   does not exist on this system or is powered off."
                   ::= { bladeTemperatureThresholdsEntry 17 }

       temperatureDASD1HardShutdown OBJECT-TYPE
                   SYNTAX  OCTET STRING
                   ACCESS  read-only
                   STATUS  mandatory
                   DESCRIPTION
                   "The blade DASD hard shutdown temperature in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 18 }

       temperatureDASD1Warning OBJECT-TYPE
                   SYNTAX  OCTET STRING
                   ACCESS  read-only
                   STATUS  mandatory
                   DESCRIPTION
                   "The blade DASD warning temperature in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 19 }

       temperatureDASD1WarningReset OBJECT-TYPE
                   SYNTAX  OCTET STRING
                   ACCESS  read-only
                   STATUS  mandatory
                   DESCRIPTION
                   "The blade DASD warning reset temperature in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 20 }

       bladeTempThresholdSensorCapability OBJECT-TYPE
                   SYNTAX  INTEGER {
                     false(0),
                     true(1)
                   }
                   ACCESS  read-only
                   STATUS  mandatory
                   DESCRIPTION
                   "Indicates whether the server blade is IPMI capable or not."
                   ::= { bladeTemperatureThresholdsEntry 21 }

       temperatureSensor1HardShutdown OBJECT-TYPE
                   SYNTAX  OCTET STRING
                   ACCESS  read-only
                   STATUS  mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 22 }

       temperatureSensor1Warning OBJECT-TYPE
                   SYNTAX  OCTET STRING
                   ACCESS  read-only
                   STATUS  mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 23 }

       temperatureSensor1WarningReset OBJECT-TYPE
                   SYNTAX  OCTET STRING
                   ACCESS  read-only
                   STATUS  mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 24 }

       temperatureSensor2HardShutdown OBJECT-TYPE
                   SYNTAX  OCTET STRING
                   ACCESS  read-only
                   STATUS  mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 25 }

       temperatureSensor2Warning OBJECT-TYPE
                   SYNTAX  OCTET STRING
                   ACCESS  read-only
                   STATUS  mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 26 }

       temperatureSensor2WarningReset OBJECT-TYPE
                   SYNTAX  OCTET STRING
                   ACCESS  read-only
                   STATUS  mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 27 }

       temperatureSensor3HardShutdown OBJECT-TYPE
                   SYNTAX  OCTET STRING
                   ACCESS  read-only
                   STATUS  mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 28 }

       temperatureSensor3Warning OBJECT-TYPE
                   SYNTAX  OCTET STRING
                   ACCESS  read-only
                   STATUS  mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 29 }

       temperatureSensor3WarningReset OBJECT-TYPE
                   SYNTAX  OCTET STRING
                   ACCESS  read-only
                   STATUS  mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 30 }

       temperatureSensor4HardShutdown OBJECT-TYPE
                   SYNTAX  OCTET STRING
                   ACCESS  read-only
                   STATUS  mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 31 }

       temperatureSensor4Warning OBJECT-TYPE
                   SYNTAX  OCTET STRING
                   ACCESS  read-only
                   STATUS  mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 32 }

       temperatureSensor4WarningReset OBJECT-TYPE
                   SYNTAX  OCTET STRING
                   ACCESS  read-only
                   STATUS  mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 33 }

       temperatureSensor5HardShutdown OBJECT-TYPE
                   SYNTAX  OCTET STRING
                   ACCESS  read-only
                   STATUS  mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 34 }

       temperatureSensor5Warning OBJECT-TYPE
                   SYNTAX  OCTET STRING
                   ACCESS  read-only
                   STATUS  mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 35 }

       temperatureSensor5WarningReset OBJECT-TYPE
                   SYNTAX  OCTET STRING
                   ACCESS  read-only
                   STATUS  mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 36 }

       temperatureSensor6HardShutdown OBJECT-TYPE
                   SYNTAX  OCTET STRING
                   ACCESS  read-only
                   STATUS  mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 37 }

       temperatureSensor6Warning OBJECT-TYPE
                   SYNTAX  OCTET STRING
                   ACCESS  read-only
                   STATUS  mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 38 }

       temperatureSensor6WarningReset OBJECT-TYPE
                   SYNTAX  OCTET STRING
                   ACCESS  read-only
                   STATUS  mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 39 }

       temperatureSensor7HardShutdown OBJECT-TYPE
                   SYNTAX  OCTET STRING
                   ACCESS  read-only
                   STATUS  mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 40 }

       temperatureSensor7Warning OBJECT-TYPE
                   SYNTAX  OCTET STRING
                   ACCESS  read-only
                   STATUS  mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 41 }

       temperatureSensor7WarningReset OBJECT-TYPE
                   SYNTAX  OCTET STRING
                   ACCESS  read-only
                   STATUS  mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 42 }

       temperatureSensor8HardShutdown OBJECT-TYPE
                   SYNTAX  OCTET STRING
                   ACCESS  read-only
                   STATUS  mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 43 }

       temperatureSensor8Warning OBJECT-TYPE
                   SYNTAX  OCTET STRING
                   ACCESS  read-only
                   STATUS  mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 44 }

       temperatureSensor8WarningReset OBJECT-TYPE
                   SYNTAX  OCTET STRING
                   ACCESS  read-only
                   STATUS  mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 45 }

       temperatureSensor9HardShutdown OBJECT-TYPE
                   SYNTAX  OCTET STRING
                   ACCESS  read-only
                   STATUS  mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 46 }

       temperatureSensor9Warning OBJECT-TYPE
                   SYNTAX  OCTET STRING
                   ACCESS  read-only
                   STATUS  mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 47 }

       temperatureSensor9WarningReset OBJECT-TYPE
                   SYNTAX  OCTET STRING
                   ACCESS  read-only
                   STATUS  mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 48 }

      bladeVoltagesTable OBJECT-TYPE
                     SYNTAX  SEQUENCE OF BladeVoltagesEntry
                     ACCESS  not-accessible
                     STATUS  mandatory
                     DESCRIPTION
                     "Table of blade voltages information."
                     ::= { bladeMonitors 5 }

       bladeVoltagesEntry OBJECT-TYPE
                     SYNTAX BladeVoltagesEntry
                     ACCESS  not-accessible
                     STATUS  mandatory
                     DESCRIPTION
                     "Blade voltages table entry"
                     INDEX { voltageIndex }
                     ::= { bladeVoltagesTable 1 }

       BladeVoltagesEntry ::= SEQUENCE {
                   voltageIndex INTEGER,
                   voltageBladeId INTEGER,
                   voltageBladeExists INTEGER,
                   voltageBladePowerState INTEGER,
                   voltageBladeName OCTET STRING,
                   bladePlus5Volt OCTET STRING,
                   bladePlus3pt3Volt OCTET STRING,
                   bladePlus12Volt OCTET STRING,
                   bladePlus2pt5Volt OCTET STRING,
                   bladePlus1pt5Volt OCTET STRING,
                   bladePlus1pt25Volt OCTET STRING,
                   bladeVRM1Volt OCTET STRING,
                   bladeSensorVoltCapability INTEGER,
                   bladeSensor1Volt OCTET STRING,
                   bladeSensor2Volt OCTET STRING,
                   bladeSensor3Volt OCTET STRING,
                   bladeSensor4Volt OCTET STRING,
                   bladeSensor5Volt OCTET STRING,
                   bladeSensor6Volt OCTET STRING,
                   bladeSensor7Volt OCTET STRING,
                   bladeSensor8Volt OCTET STRING,
                   bladeSensor9Volt OCTET STRING,
                   bladeSensor10Volt OCTET STRING,
                   bladeSensor11Volt OCTET STRING,
                   bladeSensor12Volt OCTET STRING,
                   bladeSensor13Volt OCTET STRING,
                   bladeSensor14Volt OCTET STRING,
                   bladeSensor15Volt OCTET STRING,
                   bladeSensor16Volt OCTET STRING,
                   bladeSensor17Volt OCTET STRING,
                   bladeSensor18Volt OCTET STRING,
                   bladeSensor19Volt OCTET STRING,
                   bladeSensor20Volt OCTET STRING,
                   bladeSensor21Volt OCTET STRING,
                   bladeSensor22Volt OCTET STRING,
                   bladeSensor23Volt OCTET STRING,
                   bladeSensor24Volt OCTET STRING,
                   bladeSensor25Volt OCTET STRING,
                   bladeSensor26Volt OCTET STRING,
                   bladeSensor27Volt OCTET STRING,
                   bladeSensor28Volt OCTET STRING,
                   bladeSensor29Volt OCTET STRING,
                   bladeSensor30Volt OCTET STRING
                   }

       voltageIndex  OBJECT-TYPE
                   SYNTAX  INTEGER
                   ACCESS  read-only
                   STATUS  mandatory
                   DESCRIPTION
                   "Blade voltages table index."
                   ::= { bladeVoltagesEntry 1 }


       voltageBladeId  OBJECT-TYPE
                   SYNTAX  INTEGER {
                     blade1(1),
                     blade2(2),
                     blade3(3),
                     blade4(4),
                     blade5(5),
                     blade6(6),
                     blade7(7),
                     blade8(8),
                     blade9(9),
                     blade10(10),
                     blade11(11),
                     blade12(12),
                     blade13(13),
                     blade14(14)
                   }
                   ACCESS  read-only
                   STATUS  mandatory
                   DESCRIPTION
                   "The numeric blade ID."
                   ::= { bladeVoltagesEntry 2 }

       voltageBladeExists OBJECT-TYPE
                   SYNTAX  INTEGER {
                     false(0),
                     true(1)
                   }
                   ACCESS  read-only
                   STATUS  mandatory
                   DESCRIPTION
                   "Indicates whether the server blade specified exists or not."
                   ::= { bladeVoltagesEntry 3 }

       voltageBladePowerState OBJECT-TYPE
                   SYNTAX  INTEGER {
                     off(0),
                     on(1),
                     standby(3),
                     hibernate(4),
                     unknown(255)
                   }
                   ACCESS  read-only
                   STATUS  mandatory
                   DESCRIPTION
                   "Indicates the power state of the blade specified."
                   ::= { bladeVoltagesEntry 4 }

       voltageBladeName OBJECT-TYPE
                   SYNTAX  OCTET STRING
                   ACCESS  read-only
                   STATUS  mandatory
                   DESCRIPTION
                   "The name of the blade as a null terminated string."
                   ::= { bladeVoltagesEntry 5 }

       bladePlus5Volt OBJECT-TYPE
                   SYNTAX  OCTET STRING
                   ACCESS  read-only
                   STATUS  mandatory
                   DESCRIPTION
                   "+5 Volt power supply voltage reading for the blade
                   expressed in Volts(V).  An octet string expressed as
                   'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 6 }

       bladePlus3pt3Volt OBJECT-TYPE
                   SYNTAX  OCTET STRING
                   ACCESS  read-only
                   STATUS  mandatory
                   DESCRIPTION
                   "+3.3 Volt power supply voltage reading for the blade
                   expressed in Volts(V).  An octet string expressed as
                   'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 7 }

       bladePlus12Volt OBJECT-TYPE
                   SYNTAX  OCTET STRING
                   ACCESS  read-only
                   STATUS  mandatory
                   DESCRIPTION
                   "+12 Volt power supply voltage reading for the blade
                   expressed in Volts(V).  An octet string expressed as
                   'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 8 }

       bladePlus2pt5Volt OBJECT-TYPE
                   SYNTAX  OCTET STRING
                   ACCESS  read-only
                   STATUS  mandatory
                   DESCRIPTION
                   "+2.5 Volt power supply voltage reading for the blade
                   expressed in Volts(V).  An octet string expressed as
                   'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 10 }

       bladePlus1pt5Volt OBJECT-TYPE
                   SYNTAX  OCTET STRING
                   ACCESS  read-only
                   STATUS  mandatory
                   DESCRIPTION
                   "+1.5 Volt power supply voltage reading for the blade
                   expressed in Volts(V).  An octet string expressed as
                   'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 11 }

       bladePlus1pt25Volt OBJECT-TYPE
                   SYNTAX  OCTET STRING
                   ACCESS  read-only
                   STATUS  mandatory
                   DESCRIPTION
                   "+1.25 Volt power supply voltage reading for the blade
                   expressed in Volts(V).  An octet string expressed as
                   'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 12 }

       bladeVRM1Volt OBJECT-TYPE
                   SYNTAX  OCTET STRING
                   ACCESS  read-only
                   STATUS  mandatory
                   DESCRIPTION
                   "VRM 1 voltage reading for the blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 13 }

       bladeSensorVoltCapability OBJECT-TYPE
                   SYNTAX  INTEGER {
                     false(0),
                     true(1)
                   }
                   ACCESS  read-only
                   STATUS  mandatory
                   DESCRIPTION
                   "Indicates whether the server blade is IPMI capable or not."
                   ::= { bladeVoltagesEntry 14 }

       bladeSensor1Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 15 }

       bladeSensor2Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 16 }

       bladeSensor3Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 17 }

       bladeSensor4Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 18 }

       bladeSensor5Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 19 }

       bladeSensor6Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 20 }

       bladeSensor7Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 21 }

       bladeSensor8Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 22 }

       bladeSensor9Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 23 }

       bladeSensor10Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 24 }

       bladeSensor11Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 25 }

       bladeSensor12Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 26 }

       bladeSensor13Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 27 }

       bladeSensor14Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 28 }

       bladeSensor15Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 29 }

       bladeSensor16Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 30 }

       bladeSensor17Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 31 }

       bladeSensor18Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 32 }

       bladeSensor19Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 33 }

       bladeSensor20Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 34 }

       bladeSensor21Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 35 }

       bladeSensor22Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 36 }

       bladeSensor23Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 37 }

       bladeSensor24Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 38 }

       bladeSensor25Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 39 }


       bladeSensor26Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 40 }

       bladeSensor27Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 41 }

       bladeSensor28Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 42 }

       bladeSensor29Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 43 }

       bladeSensor30Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 44 }

      bladeVoltageThresholdsTable OBJECT-TYPE
                     SYNTAX  SEQUENCE OF BladeVoltageThresholdsEntry
                     ACCESS  not-accessible
                     STATUS  mandatory
                     DESCRIPTION
                     "Table of blade VoltageThresholds information."
                     ::= { bladeMonitors 6 }

       bladeVoltageThresholdsEntry OBJECT-TYPE
                     SYNTAX BladeVoltageThresholdsEntry
                     ACCESS  not-accessible
                     STATUS  mandatory
                     DESCRIPTION
                     "Blade voltage thresholds table entry"
                     INDEX { voltageThresholdIndex }
                     ::= { bladeVoltageThresholdsTable 1 }

       BladeVoltageThresholdsEntry ::= SEQUENCE {
                   voltageThresholdIndex INTEGER,
                   voltageThresholdBladeId INTEGER,
                   voltageThresholdBladeExists INTEGER,
                   voltageThresholdBladePowerState INTEGER,
                   voltageThresholdBladeName OCTET STRING,
                   bladePlus5VoltHighWarning OCTET STRING,
                   bladePlus5VoltLowWarning OCTET STRING,
                   bladePlus3pt3VoltHighWarning OCTET STRING,
                   bladePlus3pt3VoltLowWarning OCTET STRING,
                   bladePlus12VoltHighWarning OCTET STRING,
                   bladePlus12VoltLowWarning OCTET STRING,
                   bladePlus2pt5VoltHighWarning OCTET STRING,
                   bladePlus2pt5VoltLowWarning OCTET STRING,
                   bladePlus1pt5VoltHighWarning OCTET STRING,
                   bladePlus1pt5VoltLowWarning OCTET STRING,
                   bladePlus1pt25VoltHighWarning OCTET STRING,
                   bladePlus1pt25VoltLowWarning OCTET STRING,
                   bladeVoltThresholdSensorCapability INTEGER,
                   bladeSensor1VoltHighWarning OCTET STRING,
                   bladeSensor1VoltLowWarning OCTET STRING,
                   bladeSensor2VoltHighWarning OCTET STRING,
                   bladeSensor2VoltLowWarning OCTET STRING,
                   bladeSensor3VoltHighWarning OCTET STRING,
                   bladeSensor3VoltLowWarning OCTET STRING,
                   bladeSensor4VoltHighWarning OCTET STRING,
                   bladeSensor4VoltLowWarning OCTET STRING,
                   bladeSensor5VoltHighWarning OCTET STRING,
                   bladeSensor5VoltLowWarning OCTET STRING,
                   bladeSensor6VoltHighWarning OCTET STRING,
                   bladeSensor6VoltLowWarning OCTET STRING,
                   bladeSensor7VoltHighWarning OCTET STRING,
                   bladeSensor7VoltLowWarning OCTET STRING,
                   bladeSensor8VoltHighWarning OCTET STRING,
                   bladeSensor8VoltLowWarning OCTET STRING,
                   bladeSensor9VoltHighWarning OCTET STRING,
                   bladeSensor9VoltLowWarning OCTET STRING,
                   bladeSensor10VoltHighWarning OCTET STRING,
                   bladeSensor10VoltLowWarning OCTET STRING,
                   bladeSensor11VoltHighWarning OCTET STRING,
                   bladeSensor11VoltLowWarning OCTET STRING,
                   bladeSensor12VoltHighWarning OCTET STRING,
                   bladeSensor12VoltLowWarning OCTET STRING,
                   bladeSensor13VoltHighWarning OCTET STRING,
                   bladeSensor13VoltLowWarning OCTET STRING,
                   bladeSensor14VoltHighWarning OCTET STRING,
                   bladeSensor14VoltLowWarning OCTET STRING,
                   bladeSensor15VoltHighWarning OCTET STRING,
                   bladeSensor15VoltLowWarning OCTET STRING,
                   bladeSensor16VoltHighWarning OCTET STRING,
                   bladeSensor16VoltLowWarning OCTET STRING,
                   bladeSensor17VoltHighWarning OCTET STRING,
                   bladeSensor17VoltLowWarning OCTET STRING,
                   bladeSensor18VoltHighWarning OCTET STRING,
                   bladeSensor18VoltLowWarning OCTET STRING,
                   bladeSensor19VoltHighWarning OCTET STRING,
                   bladeSensor19VoltLowWarning OCTET STRING,
                   bladeSensor20VoltHighWarning OCTET STRING,
                   bladeSensor20VoltLowWarning OCTET STRING,
                   bladeSensor21VoltHighWarning OCTET STRING,
                   bladeSensor21VoltLowWarning OCTET STRING,
                   bladeSensor22VoltHighWarning OCTET STRING,
                   bladeSensor22VoltLowWarning OCTET STRING,
                   bladeSensor23VoltHighWarning OCTET STRING,
                   bladeSensor23VoltLowWarning OCTET STRING,
                   bladeSensor24VoltHighWarning OCTET STRING,
                   bladeSensor24VoltLowWarning OCTET STRING,
                   bladeSensor25VoltHighWarning OCTET STRING,
                   bladeSensor25VoltLowWarning OCTET STRING,
                   bladeSensor26VoltHighWarning OCTET STRING,
                   bladeSensor26VoltLowWarning OCTET STRING,
                   bladeSensor27VoltHighWarning OCTET STRING,
                   bladeSensor27VoltLowWarning OCTET STRING,
                   bladeSensor28VoltHighWarning OCTET STRING,
                   bladeSensor28VoltLowWarning OCTET STRING,
                   bladeSensor29VoltHighWarning OCTET STRING,
                   bladeSensor29VoltLowWarning OCTET STRING,
                   bladeSensor30VoltHighWarning OCTET STRING,
                   bladeSensor30VoltLowWarning OCTET STRING
                   }

       voltageThresholdIndex  OBJECT-TYPE
                   SYNTAX  INTEGER
                   ACCESS  read-only
                   STATUS  mandatory
                   DESCRIPTION
                   "Blade voltage thresholds table index."
                   ::= { bladeVoltageThresholdsEntry 1 }

       voltageThresholdBladeId  OBJECT-TYPE
                   SYNTAX  INTEGER {
                     blade1(1),
                     blade2(2),
                     blade3(3),
                     blade4(4),
                     blade5(5),
                     blade6(6),
                     blade7(7),
                     blade8(8),
                     blade9(9),
                     blade10(10),
                     blade11(11),
                     blade12(12),
                     blade13(13),
                     blade14(14)
                   }
                   ACCESS  read-only
                   STATUS  mandatory
                   DESCRIPTION
                   "The numeric blade ID."
                   ::= { bladeVoltageThresholdsEntry 2 }

       voltageThresholdBladeExists OBJECT-TYPE
                   SYNTAX  INTEGER {
                     false(0),
                     true(1)
                   }
                   ACCESS  read-only
                   STATUS  mandatory
                   DESCRIPTION
                   "Indicates whether the server blade specified exists or not."
                   ::= { bladeVoltageThresholdsEntry 3 }

       voltageThresholdBladePowerState OBJECT-TYPE
                   SYNTAX  INTEGER {
                     off(0),
                     on(1),
                     standby(3),
                     hibernate(4),
                     unknown(255)
                   }
                   ACCESS  read-only
                   STATUS  mandatory
                   DESCRIPTION
                   "Indicates the power state of the blade specified."
                   ::= { bladeVoltageThresholdsEntry 4 }

       voltageThresholdBladeName OBJECT-TYPE
                   SYNTAX  OCTET STRING
                   ACCESS  read-write
                   STATUS  mandatory
                   DESCRIPTION
                   "The name of the blade as a null terminated string."
                   ::= { bladeVoltageThresholdsEntry 5 }

       bladePlus5VoltHighWarning OBJECT-TYPE
                   SYNTAX  OCTET STRING
                   ACCESS  read-only
                   STATUS  mandatory
                   DESCRIPTION
                   "Voltage warning threshold reading expressed in Volts(V).
                   If the voltage rises above this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 6 }

       bladePlus5VoltLowWarning OBJECT-TYPE
                   SYNTAX  OCTET STRING
                   ACCESS  read-only
                   STATUS  mandatory
                   DESCRIPTION
                   "Voltage warning threshold reading expressed in Volts(V).
                   If the voltage drops below this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 7 }

       bladePlus3pt3VoltHighWarning OBJECT-TYPE
                   SYNTAX  OCTET STRING
                   ACCESS  read-only
                   STATUS  mandatory
                   DESCRIPTION
                   "Voltage warning threshold reading expressed in Volts(V).
                   If the voltage rises above this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 8 }

       bladePlus3pt3VoltLowWarning OBJECT-TYPE
                   SYNTAX  OCTET STRING
                   ACCESS  read-only
                   STATUS  mandatory
                   DESCRIPTION
                   "Voltage warning threshold reading expressed in Volts(V).
                   If the voltage drops below this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 9 }

       bladePlus12VoltHighWarning OBJECT-TYPE
                   SYNTAX  OCTET STRING
                   ACCESS  read-only
                   STATUS  mandatory
                   DESCRIPTION
                   "Voltage warning threshold reading expressed in Volts(V).
                   If the voltage rises above this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 10 }

       bladePlus12VoltLowWarning OBJECT-TYPE
                   SYNTAX  OCTET STRING
                   ACCESS  read-only
                   STATUS  mandatory
                   DESCRIPTION
                   "Voltage warning threshold reading expressed in Volts(V).
                   If the voltage drops below this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 11 }

       bladePlus2pt5VoltHighWarning OBJECT-TYPE
                   SYNTAX  OCTET STRING
                   ACCESS  read-only
                   STATUS  mandatory
                   DESCRIPTION
                   "Voltage warning threshold reading expressed in Volts(V).
                   If the voltage rises above this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 14 }

       bladePlus2pt5VoltLowWarning OBJECT-TYPE
                   SYNTAX  OCTET STRING
                   ACCESS  read-only
                   STATUS  mandatory
                   DESCRIPTION
                   "Voltage warning threshold reading expressed in Volts(V).
                   If the voltage drops below this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 15 }

       bladePlus1pt5VoltHighWarning OBJECT-TYPE
                   SYNTAX  OCTET STRING
                   ACCESS  read-only
                   STATUS  mandatory
                   DESCRIPTION
                   "Voltage warning threshold reading expressed in Volts(V).
                   If the voltage rises above this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 16 }

       bladePlus1pt5VoltLowWarning OBJECT-TYPE
                   SYNTAX  OCTET STRING
                   ACCESS  read-only
                   STATUS  mandatory
                   DESCRIPTION
                   "Voltage warning threshold reading expressed in Volts(V).
                   If the voltage drops below this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 17 }

       bladePlus1pt25VoltHighWarning OBJECT-TYPE
                   SYNTAX  OCTET STRING
                   ACCESS  read-only
                   STATUS  mandatory
                   DESCRIPTION
                   "Voltage warning threshold reading expressed in Volts(V).
                   If the voltage rises above this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 18 }

       bladePlus1pt25VoltLowWarning OBJECT-TYPE
                   SYNTAX  OCTET STRING
                   ACCESS  read-only
                   STATUS  mandatory
                   DESCRIPTION
                   "Voltage warning threshold reading expressed in Volts(V).
                   If the voltage drops below this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 19 }

       bladeVoltThresholdSensorCapability OBJECT-TYPE
                   SYNTAX  INTEGER {
                     false(0),
                     true(1)
                   }
                   ACCESS  read-only
                   STATUS  mandatory
                   DESCRIPTION
                   "Indicates whether the server blade is IPMI capable or not."
                   ::= { bladeVoltageThresholdsEntry 22 }

       bladeSensor1VoltHighWarning OBJECT-TYPE
                   SYNTAX  OCTET STRING
                   ACCESS  read-only
                   STATUS  mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 23 }

       bladeSensor1VoltLowWarning OBJECT-TYPE
                   SYNTAX  OCTET STRING
                   ACCESS  read-only
                   STATUS  mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 24 }

       bladeSensor2VoltHighWarning OBJECT-TYPE
                   SYNTAX  OCTET STRING
                   ACCESS  read-only
                   STATUS  mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 25 }

       bladeSensor2VoltLowWarning OBJECT-TYPE
                   SYNTAX  OCTET STRING
                   ACCESS  read-only
                   STATUS  mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 26 }

       bladeSensor3VoltHighWarning OBJECT-TYPE
                   SYNTAX  OCTET STRING
                   ACCESS  read-only
                   STATUS  mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 27 }

       bladeSensor3VoltLowWarning OBJECT-TYPE
                   SYNTAX  OCTET STRING
                   ACCESS  read-only
                   STATUS  mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 28 }

       bladeSensor4VoltHighWarning OBJECT-TYPE
                   SYNTAX  OCTET STRING
                   ACCESS  read-only
                   STATUS  mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 29 }

       bladeSensor4VoltLowWarning OBJECT-TYPE
                   SYNTAX  OCTET STRING
                   ACCESS  read-only
                   STATUS  mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 30 }

       bladeSensor5VoltHighWarning OBJECT-TYPE
                   SYNTAX  OCTET STRING
                   ACCESS  read-only
                   STATUS  mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 31 }

       bladeSensor5VoltLowWarning OBJECT-TYPE
                   SYNTAX  OCTET STRING
                   ACCESS  read-only
                   STATUS  mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 32 }

       bladeSensor6VoltHighWarning OBJECT-TYPE
                   SYNTAX  OCTET STRING
                   ACCESS  read-only
                   STATUS  mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 33 }

       bladeSensor6VoltLowWarning OBJECT-TYPE
                   SYNTAX  OCTET STRING
                   ACCESS  read-only
                   STATUS  mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 34 }

       bladeSensor7VoltHighWarning OBJECT-TYPE
                   SYNTAX  OCTET STRING
                   ACCESS  read-only
                   STATUS  mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 35 }

       bladeSensor7VoltLowWarning OBJECT-TYPE
                   SYNTAX  OCTET STRING
                   ACCESS  read-only
                   STATUS  mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 36 }

       bladeSensor8VoltHighWarning OBJECT-TYPE
                   SYNTAX  OCTET STRING
                   ACCESS  read-only
                   STATUS  mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 37 }

       bladeSensor8VoltLowWarning OBJECT-TYPE
                   SYNTAX  OCTET STRING
                   ACCESS  read-only
                   STATUS  mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 38 }

       bladeSensor9VoltHighWarning OBJECT-TYPE
                   SYNTAX  OCTET STRING
                   ACCESS  read-only
                   STATUS  mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 39 }

       bladeSensor9VoltLowWarning OBJECT-TYPE
                   SYNTAX  OCTET STRING
                   ACCESS  read-only
                   STATUS  mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 40 }

       bladeSensor10VoltHighWarning OBJECT-TYPE
                   SYNTAX  OCTET STRING
                   ACCESS  read-only
                   STATUS  mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 41 }

       bladeSensor10VoltLowWarning OBJECT-TYPE
                   SYNTAX  OCTET STRING
                   ACCESS  read-only
                   STATUS  mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 42 }

       bladeSensor11VoltHighWarning OBJECT-TYPE
                   SYNTAX  OCTET STRING
                   ACCESS  read-only
                   STATUS  mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 43 }

       bladeSensor11VoltLowWarning OBJECT-TYPE
                   SYNTAX  OCTET STRING
                   ACCESS  read-only
                   STATUS  mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 44 }

       bladeSensor12VoltHighWarning OBJECT-TYPE
                   SYNTAX  OCTET STRING
                   ACCESS  read-only
                   STATUS  mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 45 }

       bladeSensor12VoltLowWarning OBJECT-TYPE
                   SYNTAX  OCTET STRING
                   ACCESS  read-only
                   STATUS  mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 46 }

       bladeSensor13VoltHighWarning OBJECT-TYPE
                   SYNTAX  OCTET STRING
                   ACCESS  read-only
                   STATUS  mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 47 }

       bladeSensor13VoltLowWarning OBJECT-TYPE
                   SYNTAX  OCTET STRING
                   ACCESS  read-only
                   STATUS  mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 48 }

       bladeSensor14VoltHighWarning OBJECT-TYPE
                   SYNTAX  OCTET STRING
                   ACCESS  read-only
                   STATUS  mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 49 }

       bladeSensor14VoltLowWarning OBJECT-TYPE
                   SYNTAX  OCTET STRING
                   ACCESS  read-only
                   STATUS  mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 50 }

       bladeSensor15VoltHighWarning OBJECT-TYPE
                   SYNTAX  OCTET STRING
                   ACCESS  read-only
                   STATUS  mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 51 }

       bladeSensor15VoltLowWarning OBJECT-TYPE
                   SYNTAX  OCTET STRING
                   ACCESS  read-only
                   STATUS  mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 52 }

       bladeSensor16VoltHighWarning OBJECT-TYPE
                   SYNTAX  OCTET STRING
                   ACCESS  read-only
                   STATUS  mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 53 }

       bladeSensor16VoltLowWarning OBJECT-TYPE
                   SYNTAX  OCTET STRING
                   ACCESS  read-only
                   STATUS  mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 54 }

       bladeSensor17VoltHighWarning OBJECT-TYPE
                   SYNTAX  OCTET STRING
                   ACCESS  read-only
                   STATUS  mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 55 }

       bladeSensor17VoltLowWarning OBJECT-TYPE
                   SYNTAX  OCTET STRING
                   ACCESS  read-only
                   STATUS  mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 56 }

       bladeSensor18VoltHighWarning OBJECT-TYPE
                   SYNTAX  OCTET STRING
                   ACCESS  read-only
                   STATUS  mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 57 }

       bladeSensor18VoltLowWarning OBJECT-TYPE
                   SYNTAX  OCTET STRING
                   ACCESS  read-only
                   STATUS  mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 58 }

       bladeSensor19VoltHighWarning OBJECT-TYPE
                   SYNTAX  OCTET STRING
                   ACCESS  read-only
                   STATUS  mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 59 }

       bladeSensor19VoltLowWarning OBJECT-TYPE
                   SYNTAX  OCTET STRING
                   ACCESS  read-only
                   STATUS  mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 60 }

       bladeSensor20VoltHighWarning OBJECT-TYPE
                   SYNTAX  OCTET STRING
                   ACCESS  read-only
                   STATUS  mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 61 }

       bladeSensor20VoltLowWarning OBJECT-TYPE
                   SYNTAX  OCTET STRING
                   ACCESS  read-only
                   STATUS  mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 62 }

       bladeSensor21VoltHighWarning OBJECT-TYPE
                   SYNTAX  OCTET STRING
                   ACCESS  read-only
                   STATUS  mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 63 }

       bladeSensor21VoltLowWarning OBJECT-TYPE
                   SYNTAX  OCTET STRING
                   ACCESS  read-only
                   STATUS  mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 64 }

       bladeSensor22VoltHighWarning OBJECT-TYPE
                   SYNTAX  OCTET STRING
                   ACCESS  read-only
                   STATUS  mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 65 }

       bladeSensor22VoltLowWarning OBJECT-TYPE
                   SYNTAX  OCTET STRING
                   ACCESS  read-only
                   STATUS  mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 66 }

       bladeSensor23VoltHighWarning OBJECT-TYPE
                   SYNTAX  OCTET STRING
                   ACCESS  read-only
                   STATUS  mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 67 }

       bladeSensor23VoltLowWarning OBJECT-TYPE
                   SYNTAX  OCTET STRING
                   ACCESS  read-only
                   STATUS  mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 68 }

       bladeSensor24VoltHighWarning OBJECT-TYPE
                   SYNTAX  OCTET STRING
                   ACCESS  read-only
                   STATUS  mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 69 }

       bladeSensor24VoltLowWarning OBJECT-TYPE
                   SYNTAX  OCTET STRING
                   ACCESS  read-only
                   STATUS  mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 70 }

       bladeSensor25VoltHighWarning OBJECT-TYPE
                   SYNTAX  OCTET STRING
                   ACCESS  read-only
                   STATUS  mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 71 }

       bladeSensor25VoltLowWarning OBJECT-TYPE
                   SYNTAX  OCTET STRING
                   ACCESS  read-only
                   STATUS  mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 72 }


       bladeSensor26VoltHighWarning OBJECT-TYPE
                   SYNTAX  OCTET STRING
                   ACCESS  read-only
                   STATUS  mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 73 }

       bladeSensor26VoltLowWarning OBJECT-TYPE
                   SYNTAX  OCTET STRING
                   ACCESS  read-only
                   STATUS  mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 74 }

       bladeSensor27VoltHighWarning OBJECT-TYPE
                   SYNTAX  OCTET STRING
                   ACCESS  read-only
                   STATUS  mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 75 }

       bladeSensor27VoltLowWarning OBJECT-TYPE
                   SYNTAX  OCTET STRING
                   ACCESS  read-only
                   STATUS  mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 76 }

       bladeSensor28VoltHighWarning OBJECT-TYPE
                   SYNTAX  OCTET STRING
                   ACCESS  read-only
                   STATUS  mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 77 }

       bladeSensor28VoltLowWarning OBJECT-TYPE
                   SYNTAX  OCTET STRING
                   ACCESS  read-only
                   STATUS  mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 78 }

       bladeSensor29VoltHighWarning OBJECT-TYPE
                   SYNTAX  OCTET STRING
                   ACCESS  read-only
                   STATUS  mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 79 }

       bladeSensor29VoltLowWarning OBJECT-TYPE
                   SYNTAX  OCTET STRING
                   ACCESS  read-only
                   STATUS  mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 80 }

       bladeSensor30VoltHighWarning OBJECT-TYPE
                   SYNTAX  OCTET STRING
                   ACCESS  read-only
                   STATUS  mandatory
                   DESCRIPTION
                   "Voltage warning threshold reading for IPMI blades expressed in Volts(V).
                   If the voltage rises above this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 81 }

       bladeSensor30VoltLowWarning OBJECT-TYPE
                   SYNTAX  OCTET STRING
                   ACCESS  read-only
                   STATUS  mandatory
                   DESCRIPTION
                   "Voltage warning threshold reading for IPMI blades expressed in Volts(V).
                   If the voltage drops below this value, a critical alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 82 }



      bladePowerRestart OBJECT IDENTIFIER ::= { processorBlade 6 }
       -- blade power/restart control

        bladePowerRestartTable OBJECT-TYPE
                       SYNTAX  SEQUENCE OF BladePowerRestartEntry
                       ACCESS  not-accessible
                       STATUS  mandatory
                       DESCRIPTION
                       "Table of blade remote power control information.
                       Contains power on/off enablement status for each blade."
                       ::= { bladePowerRestart 1 }

         bladePowerRestartEntry OBJECT-TYPE
                       SYNTAX BladePowerRestartEntry
                       ACCESS  not-accessible
                       STATUS  mandatory
                       DESCRIPTION
                       "Blade power restart table entry"
                       INDEX { powerRestartIndex }
                       ::= { bladePowerRestartTable 1 }

         BladePowerRestartEntry ::= SEQUENCE {
                     powerRestartIndex INTEGER,
                     powerRestartBladeId INTEGER,
                     powerRestartBladeExists INTEGER,
                     powerRestartBladePowerState INTEGER,
                     powerRestartBladeHealthState INTEGER,
                     powerRestartBladeName OCTET STRING,
                     powerOnOffBlade INTEGER,
                     restartBlade INTEGER,
                     restartBladeSMP INTEGER,
                     restartBladeNMI INTEGER,
                     restartBladeClearNVRAM INTEGER,
                     restartBladeInvokeDiags INTEGER,
                     restartBladeInvokeDiagsFromDefaultBootList INTEGER,
                     restartBladeToSMSBootMenu INTEGER,
                     bladePowerEnableSMSBootMenu INTEGER
                     }

         powerRestartIndex  OBJECT-TYPE
                     SYNTAX  INTEGER
                     ACCESS  read-only
                     STATUS  mandatory
                     DESCRIPTION
                     "Blade power restart table index."
                     ::= { bladePowerRestartEntry 1 }

         powerRestartBladeId  OBJECT-TYPE
                     SYNTAX  INTEGER {
                       blade1(1),
                       blade2(2),
                       blade3(3),
                       blade4(4),
                       blade5(5),
                       blade6(6),
                       blade7(7),
                       blade8(8),
                       blade9(9),
                       blade10(10),
                       blade11(11),
                       blade12(12),
                       blade13(13),
                       blade14(14)
                     }
                     ACCESS  read-only
                     STATUS  mandatory
                     DESCRIPTION
                     "The numeric blade ID."
                     ::= { bladePowerRestartEntry 2 }

         powerRestartBladeExists OBJECT-TYPE
                     SYNTAX  INTEGER {
                       false(0),
                       true(1)
                     }
                     ACCESS  read-only
                     STATUS  mandatory
                     DESCRIPTION
                     "Indicates whether the server blade specified exists or not."
                     ::= { bladePowerRestartEntry 3 }

         powerRestartBladePowerState OBJECT-TYPE
                     SYNTAX  INTEGER {
                       off(0),
                       on(1),
                       standby(3),
                       hibernate(4),
                       unknown(255)
                     }
                     ACCESS  read-only
                     STATUS  mandatory
                     DESCRIPTION
                     "Indicates the power state of the blade specified.
                      If the state cannot be determined, the unknown(255) is returned."
                     ::= { bladePowerRestartEntry 4 }

         powerRestartBladeHealthState  OBJECT-TYPE
                   SYNTAX  INTEGER {
                     unknown(0),
                     good(1),
                     warning(2),
                     critical(3),
                     kernelMode(4),
                     discovering(5),
                     commError(6),
                     noPower(7),
                     flashing(8),
                     initFailure(9),
                     insufficientPower(10),
                     powerDenied(11),
                     maintMode(12),
                     firehoseDump(13)
                   }
                   ACCESS  read-only
                   STATUS  mandatory
                   DESCRIPTION
                   "The system health state for the blade.

                    Unknown: Blade is in an undefined state.
                    Good: Blade is operating normally.
                    Warning: One or more outstanding warnings exist for this blade.
                    Critical: One or more outstanding critical events for this blade.
                    Kernel Mode: Blade is in kernel mode.
                    Discovering: The MM is currently in the process of discovering this blade.
                    Communications Error: The MM failed to communicate with this blade.
                    No Power: No power to the blade's domain.
                    Flashing: Flashing in progress.
                    Initialization Failure: Blade failed to initialized.
                    Insufficient Power: Not enough power is left in the blade's domain to power the blade.
                    Power Denied: Power was denied to the blade."
                   ::= { bladePowerRestartEntry 5 }

         powerRestartBladeName OBJECT-TYPE
                     SYNTAX  OCTET STRING
                     ACCESS  read-only
                     STATUS  mandatory
                     DESCRIPTION
                     "The name of the blade as a null terminated string."
                     ::= { bladePowerRestartEntry 6 }

         powerOnOffBlade OBJECT-TYPE
                     SYNTAX  INTEGER {
                       off(0),
                       on(1),
                       softoff(2)
                     }
                     ACCESS  read-write
                     STATUS  mandatory
                     DESCRIPTION
                     "Control the power state of a specific blade.

                     Off: Power Off Blade.
                     On:  Power On Blade.
                     Softoff: Shut Down OS and Power Off Blade. This operation is not
                              supported on all blades.

                     NOTE: Value returned for the GET command is meaningless
                     for this MIB object. The powerRestartBladePowerState MIB object should be
                     used to check the power state of the blade(s)"
                     ::= { bladePowerRestartEntry 7 }

         restartBlade OBJECT-TYPE
                     SYNTAX  INTEGER {
                       execute(1)
                     }
                     ACCESS  read-write
                     STATUS  mandatory
                     DESCRIPTION
                     "Restart a blade.

                     NOTE: Value returned for the GET command is meaningless
                     for this MIB object."
                     ::= { bladePowerRestartEntry 8 }

         restartBladeSMP OBJECT-TYPE
                     SYNTAX  INTEGER {
                       execute(1)
                     }
                     ACCESS  read-write
                     STATUS  mandatory
                     DESCRIPTION
                     "Restart a blade's system management processor.

                     NOTE: Value returned for the GET command is meaningless
                     for this MIB object."
                     ::= { bladePowerRestartEntry 9 }

         restartBladeNMI OBJECT-TYPE
                     SYNTAX  INTEGER {
                       execute(1)
                     }
                     ACCESS  read-write
                     STATUS  mandatory
                     DESCRIPTION
                     "Issue an NMI to the blade.  This option is not supported
                     on all blades.

                     NOTE: Value returned for the GET command is meaningless
                     for this MIB object."
                     ::= { bladePowerRestartEntry 10 }

         restartBladeClearNVRAM OBJECT-TYPE
                     SYNTAX  INTEGER {
                       execute(1)
                     }
                     ACCESS  read-write
                     STATUS  mandatory
                     DESCRIPTION
                     "Restart a blade and set NVRAM to default values.  This option is not
                     supported on all blades.

                     NOTE: Value returned for the GET command is meaningless
                     for this MIB object."
                     ::= { bladePowerRestartEntry 11 }

         restartBladeInvokeDiags OBJECT-TYPE
                     SYNTAX  INTEGER {
                       execute(1)
                     }
                     ACCESS  read-write
                     STATUS  mandatory
                     DESCRIPTION
                     "Restart a blade and boot into diagnostic mode.  This option is not
                     supported on all blades.

                     NOTE: Value returned for the GET command is meaningless
                     for this MIB object."
                     ::= { bladePowerRestartEntry 12 }

         restartBladeInvokeDiagsFromDefaultBootList OBJECT-TYPE
                     SYNTAX  INTEGER {
                       execute(1)
                     }
                     ACCESS  read-write
                     STATUS  mandatory
                     DESCRIPTION
                     "Restart a blade and boot into diagnostic mode from Default Boot List
                     as defined on the blade.  This option is not supported on all blades.

                     NOTE: Value returned for the GET command is meaningless
                     for this MIB object."
                     ::= { bladePowerRestartEntry 13 }

         restartBladeToSMSBootMenu OBJECT-TYPE
                        SYNTAX  INTEGER {
                       execute(1)
                     }
                     ACCESS  read-write
                     STATUS  deprecated
                     DESCRIPTION
                     "Restart a blade to SMS boot menu. This option is not supported on
                     all blades, and at the time of this MIB definition was only supported on 
                     POWER blades.

                     This object is deprecated and please use the bladePowerEnableSMSBootMenu
                     object.   

                     NOTE: Value returned for the GET command is meaningless
                     for this MIB object."
                     ::= { bladePowerRestartEntry 14 }

          bladePowerEnableSMSBootMenu OBJECT-TYPE
                        SYNTAX  INTEGER {
                        disabled(0),
                        enabled(1)
                     }
                     ACCESS  read-write
                     STATUS  mandatory
                     DESCRIPTION
                     "Enables/disables a blade restart to the SMS boot menu.
                      Setting this object to 'enable(1)' will cause a reboot of 
                      the node to the SMS menu.
                      This option is not supported by all blades, and at the time of 
                      this MIB definition was only supported on POWER blades."
                     ::= { bladePowerRestartEntry 15 }

      bladeConfiguration OBJECT IDENTIFIER ::= { processorBlade 7 }
       -- blade power/restart control

        bladeConfigurationTable OBJECT-TYPE
                       SYNTAX  SEQUENCE OF BladeConfigurationEntry
                       ACCESS  not-accessible
                       STATUS  mandatory
                       DESCRIPTION
                       "Table of blade configuration information.
                       Contains boot mode and auto power on/off settings for each 
                       blade."
                       ::= { bladeConfiguration 1 }

         bladeConfigurationEntry OBJECT-TYPE
                       SYNTAX BladeConfigurationEntry
                       ACCESS  not-accessible
                       STATUS  mandatory
                       DESCRIPTION
                       "Blade configuration table entry"
                       INDEX { configurationIndex }
                       ::= { bladeConfigurationTable 1 }

         BladeConfigurationEntry ::= SEQUENCE {
                     configurationIndex INTEGER,
                     configurationBladeId INTEGER,
                     configurationBladeExists INTEGER,
                     configurationBladePowerState INTEGER,
                     configurationBladeName OCTET STRING,
                     configurationBladeActiveBootMode INTEGER,
                     configurationBladePendingBootMode INTEGER,
                     configurationBladeAutoPowerOn INTEGER,
                     configurationBladePowerOnRestartDelay INTEGER
                     }

         configurationIndex  OBJECT-TYPE
                     SYNTAX  INTEGER
                     ACCESS  read-only
                     STATUS  mandatory
                     DESCRIPTION
                     "Blade configuration table index."
                     ::= { bladeConfigurationEntry 1 }

         configurationBladeId  OBJECT-TYPE
                     SYNTAX  INTEGER {
                       blade1(1),
                       blade2(2),
                       blade3(3),
                       blade4(4),
                       blade5(5),
                       blade6(6),
                       blade7(7),
                       blade8(8),
                       blade9(9),
                       blade10(10),
                       blade11(11),
                       blade12(12),
                       blade13(13),
                       blade14(14)
                     }
                     ACCESS  read-only
                     STATUS  mandatory
                     DESCRIPTION
                     "The numeric blade ID."
                     ::= { bladeConfigurationEntry 2 }

         configurationBladeExists OBJECT-TYPE
                     SYNTAX  INTEGER {
                       false(0),
                       true(1)
                     }
                     ACCESS  read-only
                     STATUS  mandatory
                     DESCRIPTION
                     "Indicates whether the server blade specified exists or not."
                     ::= { bladeConfigurationEntry 3 }

         configurationBladePowerState OBJECT-TYPE
                     SYNTAX  INTEGER {
                       off(0),
                       on(1),
                       standby(3),
                       hibernate(4),
                       unknown(255)
                     }
                     ACCESS  read-only
                     STATUS  mandatory
                     DESCRIPTION
                     "Indicates the power state of the blade specified."
                     ::= { bladeConfigurationEntry 4 }

         configurationBladeName OBJECT-TYPE
                     SYNTAX  OCTET STRING
                     ACCESS  read-write
                     STATUS  mandatory
                     DESCRIPTION
                     "The name of the blade as a null terminated string."
                     ::= { bladeConfigurationEntry 5 }

         configurationBladeActiveBootMode OBJECT-TYPE
                     SYNTAX  INTEGER {
                       temporary(1),
                       permanent(2),
                       notApplicable(255)
                     }
                     ACCESS  read-only
                     STATUS  mandatory
                     DESCRIPTION
                     "Indicates the active copy of the firmware from which the blade is booting.
                     NOTE: Some blades do not support the automatic boot recovery. It displays
                     'notApplicable' for such blades.
                     Booting from the temporary copy is recommended since it typically contains the
                     latest enhancements and fixes. Switching to the permanent copy should be reserved
                     for when booting from the temporary copy is no longer possible."
                     ::= { bladeConfigurationEntry 7 }

         configurationBladePendingBootMode OBJECT-TYPE
                     SYNTAX  INTEGER {
                       temporary(1),
                       permanent(2),
                       notApplicable(255)
                     }
                     ACCESS  read-write
                     STATUS  mandatory
                     DESCRIPTION
                     "Indicates the copy of the firmware from which the blade will boot
                     after the next reboot.
                     NOTE: Some blades do not support the automatic boot recovery. It displays
                     'notApplicable' for such blades and the value can not be set.
                     Booting from the temporary copy is recommended since it typically contains the
                     latest enhancements and fixes. Switching to the permanent copy should be reserved
                     for when booting from the temporary copy is no longer possible."
                     ::= { bladeConfigurationEntry 8 }

         configurationBladeAutoPowerOn OBJECT-TYPE
                     SYNTAX  INTEGER {
                       restore(1),
                       auto(2),
                       manual(3),
                       notApplicable(255)
                     }
                     ACCESS  read-write
                     STATUS  mandatory
                     DESCRIPTION
                     "Blade auto-power on policy.
                       - restore: blade will be powered on which were previously on.
                       - auto:    blade will automatically be powered on when power is applied to the chassis.
                       - manual:  blade will be left off until manually powered on by the user.
                       - notApplicable: is a read-only value, this value cannot be set."
                     ::= { bladeConfigurationEntry 9 }

         configurationBladePowerOnRestartDelay OBJECT-TYPE
                     SYNTAX  INTEGER (0..32767)
                     ACCESS  read-write
                     STATUS  mandatory
                     DESCRIPTION
                     "Restart delay (in seconds) when power is applied to a blade."
                     ::= { bladeConfigurationEntry 10 }

        -- Power Management Policy Settings
        bladePowerManagementPolicy OBJECT IDENTIFIER ::= { bladeConfiguration 2 }

          powerManagementPolicy OBJECT-TYPE
                     SYNTAX  INTEGER {
                       power-module-redundancy(0),
                       power-module-redundancy-throttle(1),
                       basic(2),
                       power-source-redundancy(16),
                       power-source-redundancy-throttle(17)
                     }
                     ACCESS  read-write
                     STATUS  mandatory
                     DESCRIPTION
                        "Power Module Redundancy
                        
                        Intended for a single power source into the chassis where each
                        Power Module is on its own dedicated circuit. Maximum power is 
                        limited to one less than the number of Power Modules when more 
                        than one Power Module is present. One Power Module can fail 
                        without affecting compute node operation. Multiple Power Module 
                        failures can cause the chassis to power off. Note that some compute
                        nodes may not be allowed to power on if doing so would exceed the
                        policy power limit.
                              
                        Power Module Redundancy with Compute Nodes Throttling Allowed
                        
                        Very similar to Power Module Redundancy. This policy allows for a 
                        higher power limit; however, capable compute nodes may be allowed 
                        to throttle down if one Power Module fails.
                               
                        Basic Power Management
                        
                        Maximum power limit is higher than other policies and is limited 
                        only by the nameplate power of all the Power Modules combined. 
                        This is the least conservative approach, since it does not provide 
                        any protection for power source or Power Module failure. If any
                        single power supply fails, compute node and/or chassis operation 
                        may be affected.

                        Power Source Redundancy

                        Intended for dual power sources into the chassis. Maximum power is
                        limited to the capacity of half the number of installed power modules. 
                        This is the most conservative approach and is recommended when all power 
                        modules are installed. When the chassis is correctly wired with dual
                        power sources, one power source can fail without affecting compute
                        node server operation. Note that some compute nodes may not be allowed 
                        to power on if doing so would exceed the policy power limit.
                           
                        Power Source Redundancy with Compute Node Throttling Allowed
                        
                        Very similar to the Power Source Redundancy. This policy allows
                        for a higher power limit, however capable compute nodes may be allowed
                        to throttle down if one power source fails.

                        Please see the powerPolicyTable for more information regarding this setting."
                     ::= { bladePowerManagementPolicy 1 }

          acousticMode OBJECT-TYPE
                     SYNTAX  INTEGER {
                       disabled(0),
                       acoustic-quiet-level1(1),
                       acoustic-quiet-level2(2),
                       acoustic-quiet-level3(3),
                       acoustic-quiet-level4(4),
                       acoustic-quiet-level5(5)
                     }
                     ACCESS  read-write
                     STATUS  mandatory
                     DESCRIPTION
                     "Acoustic mode setting for thermal conditions.  A setting
                     of disabled (0), disables this feature.  A setting of
                     acoustic-quiet-level1 (5) is the least restrictive and the
                     least quiet sound level.  A setting of
                     acoustic-quiet-level5 (1) is the most restrictive and 
                     the most quiet sound level. Some values may not be valid on
                     some chassis.  A bad value will be returned in this case.
 
                     NOTE: On a telco chassis, when telcoNEBSCoolingOverride is enabled, 
                           this acoustic mode is disabled and cannot be updated."
                     ::= { bladePowerManagementPolicy 3 }

      bladeBootCountPowerOnTime OBJECT IDENTIFIER ::= { processorBlade 10 }
       -- blade Count of number of boots for a blade and its Power On Time

        bladeBootCountPowerOnTimeTable OBJECT-TYPE
                       SYNTAX  SEQUENCE OF BladeBootCountPowerOnTimeEntry
                       ACCESS  not-accessible
                       STATUS  mandatory
                       DESCRIPTION
                       "Table per blade of the number of boots for the blade and
                       the number of seconds the blade has been powered on."
                       ::= { bladeBootCountPowerOnTime 1 }

         bladeBootCountPowerOnTimeEntry OBJECT-TYPE
                       SYNTAX BladeBootCountPowerOnTimeEntry
                       ACCESS  not-accessible
                       STATUS  mandatory
                       DESCRIPTION
                       "The number of boots for the blade and
                       the number of seconds the blade has been powered on."
                       INDEX { bootCountPowerOnTimeBladeIndex }
                       ::= { bladeBootCountPowerOnTimeTable 1 }

         BladeBootCountPowerOnTimeEntry ::= SEQUENCE {
                   bootCountPowerOnTimeBladeIndex INTEGER,
                   bootCountPowerOnTimeBladeId    INTEGER,
                   bootCountPowerOnTimeBoots      INTEGER,
                   bootCountPowerOnTimeSecs       INTEGER
                   }

         bootCountPowerOnTimeBladeIndex  OBJECT-TYPE
                     SYNTAX  INTEGER
                     ACCESS  read-only
                     STATUS  mandatory
                     DESCRIPTION
                     "Blade boot count/Power On Time table index."
                     ::= { bladeBootCountPowerOnTimeEntry 1 }

         bootCountPowerOnTimeBladeId  OBJECT-TYPE
                     SYNTAX  INTEGER {
                       blade1(1),
                       blade2(2),
                       blade3(3),
                       blade4(4),
                       blade5(5),
                       blade6(6),
                       blade7(7),
                       blade8(8),
                       blade9(9),
                       blade10(10),
                       blade11(11),
                       blade12(12),
                       blade13(13),
                       blade14(14)
                     }
                     ACCESS  read-only
                     STATUS  mandatory
                     DESCRIPTION
                     "The numeric blade ID."
                     ::= { bladeBootCountPowerOnTimeEntry 2 }

         bootCountPowerOnTimeBoots  OBJECT-TYPE
                     SYNTAX  INTEGER
                     ACCESS  read-write
                     STATUS  mandatory
                     DESCRIPTION
                     "Blade Boot Count. If there is no blade in the
                     given slot then this value is undefined. Writing this
                     value resets the Boot Count to zero."
                     ::= { bladeBootCountPowerOnTimeEntry 3 }

         bootCountPowerOnTimeSecs  OBJECT-TYPE
                     SYNTAX  INTEGER
                     ACCESS  read-write
                     STATUS  mandatory
                     DESCRIPTION
                     "Blade Power On Time in seconds. If there is no blade in
                     the given slot then this value is undefined. Writing this
                     value resets the Power On Time to zero."
                     ::= { bladeBootCountPowerOnTimeEntry 4 }

      bladeVlanId OBJECT-TYPE
                  SYNTAX  INTEGER
                  ACCESS  read-write
                  STATUS  mandatory
                  DESCRIPTION
                  "This is the virtual LAN ID for the internal management network between the MM and
                  the blade system management processors (BSMPs).  The range of valid VLAN ID's
                  is 3 to 4095."
                  ::= { processorBlade 11 }

        ---
        --- Blade Bay Data Table MIB objects
        ---
        bladeBayDataTable OBJECT-TYPE
                SYNTAX SEQUENCE OF BladeBayDataEntry
                ACCESS not-accessible
                STATUS mandatory
                DESCRIPTION
                        "Table of blade bay data (BBD) information."
                ::= { processorBlade 13 }

        bladeBayDataEntry OBJECT-TYPE
                SYNTAX BladeBayDataEntry
                ACCESS not-accessible
                STATUS mandatory
                DESCRIPTION
                        "Blade bay data (BBD) table entry."
                INDEX { bayDataIndex }
                ::= { bladeBayDataTable 1 }

        BladeBayDataEntry ::= SEQUENCE {
                bayDataIndex INTEGER,
                bayDataBladeId INTEGER,
                bayDataBladeExists INTEGER,
                bayDataBladePowerState INTEGER,
                bayDataBladeName OCTET STRING,
                bayData OCTET STRING,
                bayDataBladeStatus INTEGER
                }

        bayDataIndex OBJECT-TYPE
                SYNTAX INTEGER
                ACCESS read-only
                STATUS mandatory
                DESCRIPTION
                        "Blade bay data (BBD) table index."
                ::= { bladeBayDataEntry 1 }

        bayDataBladeId OBJECT-TYPE
                SYNTAX INTEGER {
                        blade1(1),
                        blade2(2),
                        blade3(3),
                        blade4(4),
                        blade5(5),
                        blade6(6),
                        blade7(7),
                        blade8(8),
                        blade9(9),
                        blade10(10),
                        blade11(11),
                        blade12(12),
                        blade13(13),
                        blade14(14)
                }
                ACCESS read-only
                STATUS mandatory
                DESCRIPTION
                        "The numeric blade ID."
                ::= { bladeBayDataEntry 2 }

        bayDataBladeExists OBJECT-TYPE
                SYNTAX INTEGER {
                        false(0),
                        true(1)
                }
                ACCESS read-only
                STATUS mandatory
                DESCRIPTION
                        "Indicates whether the server blade specified exists or not."
                ::= { bladeBayDataEntry 3 }

        bayDataBladePowerState OBJECT-TYPE
                SYNTAX INTEGER {
                        off(0),
                        on(1),
                        standby(3),
                        hibernate(4),
                        unknown(255)
                }
                ACCESS read-only
                STATUS mandatory
                DESCRIPTION
                        "Indicates the power state of the blade specified."
                ::= { bladeBayDataEntry 4 }

        bayDataBladeName OBJECT-TYPE
                SYNTAX OCTET STRING
                ACCESS read-only
                STATUS mandatory
                DESCRIPTION
                        "The name of the blade as a null terminated string."
                ::= { bladeBayDataEntry 5 }


        bayData OBJECT-TYPE
                SYNTAX OCTET STRING
                ACCESS read-write
                STATUS mandatory
                DESCRIPTION
                        "A null terminated string that defines the Blade Bay Data (BBD). This data
                        is pushed to the blade's BSMP and SMBIOS structures, where it can used
                        by the blade's OS. Up to 60 characters can be defined plus a Null
                        terminator."
                ::= { bladeBayDataEntry 6 }

        bayDataBladeStatus OBJECT-TYPE
                SYNTAX INTEGER {
                        supported(0),
                        bsmp(1),
                        notPresent(2),
                        discovering(3),
                        notApplicable(255)
                }
                ACCESS read-only
                STATUS mandatory
                DESCRIPTION
                        "This shows Blade Bay Data (BBD) status. 0 means the blade fully
                        supports BBD; 1 means that the blade's BIOS does not support BBD;
                        2 means that there is no blade in the bay; 3 means that the blade is
                        being discovered. 255 means that the blade does not support BBD."
                ::= { bladeBayDataEntry 7 }


      bladeNetworkConfiguration  OBJECT IDENTIFIER ::= { processorBlade 12 }
      -- blade network configuration for all blades

        bladeIPv4ConfigTable OBJECT-TYPE
                       SYNTAX  SEQUENCE OF BladeIPv4ConfigEntry
                       ACCESS  not-accessible
                       STATUS  mandatory
                       DESCRIPTION
                       "Table of all blades' network interfaces."
                       ::= { bladeNetworkConfiguration 5 }

         bladeIPv4ConfigEntry OBJECT-TYPE
                       SYNTAX  BladeIPv4ConfigEntry
                       ACCESS  not-accessible
                       STATUS  mandatory
                       DESCRIPTION
                       "Blade configuration table entry"
                       INDEX { bladeIPv4ConfigIndex, bladeIPv4ConfigPortIndex }
                       ::= { bladeIPv4ConfigTable 1 }

         BladeIPv4ConfigEntry ::= SEQUENCE {
                     bladeIPv4ConfigIndex INTEGER,
                     bladeIPv4ConfigPortIndex INTEGER,
                     bladeIPv4ConfigPortLabel OCTET STRING,
                     bladeIPv4ConfigPhysicalLinkStatus INTEGER,
                     bladeIPv4ConfigPhysicalLinkState INTEGER,
                     bladeIPv4ConfigIPAddr IpAddress,
                     bladeIPv4ConfigSubnetMask IpAddress,
                     bladeIPv4ConfigGatewayAddr IpAddress,
                     bladeIPv4ConfigVlanId INTEGER,
                     bladeIPv4ConfigDHCPEnable INTEGER,
                     bladeIPv4ConfigMACAddr OCTET STRING
                     }

         bladeIPv4ConfigIndex  OBJECT-TYPE
                     SYNTAX  INTEGER
                     ACCESS  read-only
                     STATUS  mandatory
                     DESCRIPTION
                     "The blade's slot number."
                     ::= { bladeIPv4ConfigEntry 1 }

         bladeIPv4ConfigPortIndex OBJECT-TYPE
                     SYNTAX  INTEGER
                     ACCESS  read-only
                     STATUS  mandatory
                     DESCRIPTION
                     "The physical port number of the given entry."
                     ::= { bladeIPv4ConfigEntry 2 }

         bladeIPv4ConfigPortLabel OBJECT-TYPE
                     SYNTAX  OCTET STRING
                     ACCESS  read-only
                     STATUS  mandatory
                     DESCRIPTION
                     "Show string label that identifies the interface."
                     ::= { bladeIPv4ConfigEntry 3 }

         bladeIPv4ConfigPhysicalLinkStatus OBJECT-TYPE
                     SYNTAX  INTEGER {
                       down(0),
                       up(1),
                       notApplicable(255)
                     }
                     ACCESS  read-only
                     STATUS  mandatory
                     DESCRIPTION
                     "Indicates whether this network interface port is up or down.
                     If this network interface doesn't support up/down, show
                     'notApplicable(255)'."
                     ::= { bladeIPv4ConfigEntry 4 }

         bladeIPv4ConfigPhysicalLinkState OBJECT-TYPE
                     SYNTAX  INTEGER {
                       down(0),
                       up(1),
                       loopback(2),
                       notApplicable(255)
                     }
                     ACCESS  read-write
                     STATUS  mandatory
                     DESCRIPTION
                     "Configuration object for requesting the physical port
                     to be either, down(0), up(1) or loopback(2). To get the
                     current status of a physical port, use the object,
                     bladeIPv4ConfigPhysicalLinkStatus.
                     If this network interface doesn't support up/down/loopback,
                     show 'notApplicable(255)'."
                     ::= { bladeIPv4ConfigEntry 5 }

         bladeIPv4ConfigIPAddr OBJECT-TYPE
                     SYNTAX  IpAddress
                     ACCESS  read-write
                     STATUS  mandatory
                     DESCRIPTION
                     "Show/modify current IP address of the blade network
                     interface.  Note that only if the
                     bladeIPv4ConfigPhysicalLinkStatus is 'up(1)' and the
                     bladeIPv4ConfigDHCPEnable is not 'useDhcp(1)', should the
                     IP address be pushed down to blade System Management
                     Processor."
                     ::= { bladeIPv4ConfigEntry 6 }

         bladeIPv4ConfigSubnetMask OBJECT-TYPE
                     SYNTAX  IpAddress
                     ACCESS  read-write
                     STATUS  mandatory
                     DESCRIPTION
                     "Show or modifie current subnet mask of the blade network
                     interface.  Note that only if the
                     bladeIPv4ConfigPhysicalLinkStatus is 'up(1)' and the
                     bladeIPv4ConfigDHCPEnable is not 'useDhcp(1)', should the
                     IP address be pushed down to blade System Management
                     Processor."
                     ::= { bladeIPv4ConfigEntry 7 }

         bladeIPv4ConfigGatewayAddr OBJECT-TYPE
                     SYNTAX  IpAddress
                     ACCESS  read-write
                     STATUS  mandatory
                     DESCRIPTION
                     "Show or modify current IP gateway of the blade network
                     interface.  Note that only if the
                     bladeIPv4ConfigPhysicalLinkStatus is 'up(1)' and the
                     bladeIPv4ConfigDHCPEnable is not 'useDhcp(1)', should the
                     IP address be pushed down to blade System Management
                     Processor."
                     ::= { bladeIPv4ConfigEntry 8 }

         bladeIPv4ConfigVlanId   OBJECT-TYPE
                     SYNTAX  INTEGER
                      ACCESS  read-write
                      STATUS  mandatory
                      DESCRIPTION
                      "This is the Virtual LAN ID for supported network
                      interface cards (NICs).  The range of valid VLAN ID's
                      is 0 to 4095."
                      ::= { bladeIPv4ConfigEntry 9 }

         bladeIPv4ConfigDHCPEnable OBJECT-TYPE
                     SYNTAX  INTEGER {
                        useStatic(0),
                        useDhcp(1),
                        tryDhcpThenTryStatic(2),
                        notApplicable(255)
                     }
                     ACCESS  read-write
                     STATUS  mandatory
                     DESCRIPTION
                     "IP config method on the blade network interface to modify
                     mode to static IP, DHCP and 'try DHCP then try static'.
                     If this network interface doesn't support DHCP, show
                     'notApplicable(255)'."
                     ::= { bladeIPv4ConfigEntry 10 }

         bladeIPv4ConfigMACAddr OBJECT-TYPE
                     SYNTAX  OCTET STRING
                     ACCESS  read-only
                     STATUS  mandatory
                     DESCRIPTION
                     "Show the blade network interface MAC address. If this
                     network interface doesn't support MAC, show
                     'notApplicable'."
                     ::= { bladeIPv4ConfigEntry 11 }

      bladeIPv6Config  OBJECT IDENTIFIER ::= { bladeNetworkConfiguration 10 }

           bladeIPv6ConfigTable OBJECT-TYPE
                      SYNTAX  SEQUENCE OF BladeIPv6ConfigEntry
                      ACCESS  not-accessible
                      STATUS  mandatory
                      DESCRIPTION
                      "A table of IPv6 configuration options for blades.

                      NOTE: This MIB object is not applicable to blades that
                      do not support IPv6."
                      ::= { bladeIPv6Config 1 }

           bladeIPv6ConfigEntry  OBJECT-TYPE
                         SYNTAX BladeIPv6ConfigEntry
                         ACCESS  not-accessible
                         STATUS  mandatory
                         DESCRIPTION
                         "IPv6 configuration options for a blade.

                         NOTE: This MIB object is not applicable to blades that
                         do not support IPv6."
                         INDEX { bladeIPv6ConfigIndex, bladeIPv6ConfigPortIndex }
                         ::= { bladeIPv6ConfigTable 1 }

           BladeIPv6ConfigEntry ::= SEQUENCE {
                       bladeIPv6ConfigIndex INTEGER,
                       bladeIPv6ConfigPortIndex INTEGER,
                       bladeIPv6ConfigEnabled INTEGER,
                       bladeIPv6ConfigStatic INTEGER,
                       bladeDHCPv6ConfigEnabled INTEGER,
                       bladeIPv6ConfigStatelessEnabled INTEGER
                       }

           bladeIPv6ConfigIndex OBJECT-TYPE
                       SYNTAX  INTEGER
                       ACCESS  read-only
                       STATUS  mandatory
                       DESCRIPTION
                       "The blade's slot number"
                       ::= { bladeIPv6ConfigEntry 1 }

           bladeIPv6ConfigPortIndex OBJECT-TYPE
                       SYNTAX  INTEGER
                       ACCESS  read-only
                       STATUS  mandatory
                       DESCRIPTION
                       "The physical port number of the given entry"
                       ::= { bladeIPv6ConfigEntry 2 }

           bladeIPv6ConfigEnabled OBJECT-TYPE
                       SYNTAX  INTEGER { disable(0),enable(1) }
                       ACCESS  read-write
                       STATUS  mandatory
                       DESCRIPTION
                       "Enables/Disables IPv6 support on the blade."
                       ::= { bladeIPv6ConfigEntry 3 }

           bladeIPv6ConfigStatic OBJECT-TYPE
                       SYNTAX  INTEGER { disable(0),enable(1) }
                       ACCESS  read-write
                       STATUS  mandatory
                       DESCRIPTION
                       "Enables/Disables IPv6 static configuration support on the blade."
                       ::= { bladeIPv6ConfigEntry 4 }

           bladeDHCPv6ConfigEnabled OBJECT-TYPE
                       SYNTAX  INTEGER { disable(0),enable(1) }
                       ACCESS  read-write
                       STATUS  mandatory
                       DESCRIPTION
                       "Enables/Disables DHCPv6 address configuration support on the blade."
                       ::= { bladeIPv6ConfigEntry 5 }

           bladeIPv6ConfigStatelessEnabled OBJECT-TYPE
                       SYNTAX  INTEGER { disable(0),enable(1) }
                       ACCESS  read-write
                       STATUS  mandatory
                       DESCRIPTION
                       "Enables/Disables IPv6 stateless auto-configuration support on the blade."
                       ::= { bladeIPv6ConfigEntry 6 }

        bladeIPv6AddressTable OBJECT-TYPE
                      SYNTAX  SEQUENCE OF BladeIPv6AddressEntry
                      ACCESS  not-accessible
                      STATUS  mandatory
                      DESCRIPTION
                      "A table of assigned IPv6 addresses for blades.

                      NOTE: This MIB object is not applicable to blades that
                      do not support IPv6."
                      ::= { bladeIPv6Config 2 }

           bladeIPv6AddressEntry  OBJECT-TYPE
                         SYNTAX BladeIPv6AddressEntry
                         ACCESS  not-accessible
                         STATUS  mandatory
                         DESCRIPTION
                         "The assigned IPv6 address for a given blade.

                         NOTE: This MIB object is not applicable to blades that
                         do not support IPv6."
                         INDEX { bladeIPv6AddressIndex, bladeIPv6AddressPortIndex, bladeIPv6AddressEntryIndex}
                         ::= { bladeIPv6AddressTable 1 }

           BladeIPv6AddressEntry ::= SEQUENCE {
                       bladeIPv6AddressIndex          INTEGER,
                       bladeIPv6AddressPortIndex      INTEGER,
                       bladeIPv6AddressEntryIndex     INTEGER,
                       bladeIPv6AddressType           INTEGER,
                       bladeIPv6Address               InetAddressIPv6,
                       bladeIPv6AddressPrefixLen      INTEGER,
                       bladeIPv6AddressDefaultRoute   InetAddressIPv6
                       }

           bladeIPv6AddressIndex OBJECT-TYPE
                       SYNTAX  INTEGER
                       ACCESS  read-only
                       STATUS  mandatory
                       DESCRIPTION
                       "The blade's slot number."
                       ::= { bladeIPv6AddressEntry 1 }

           bladeIPv6AddressPortIndex OBJECT-TYPE
                       SYNTAX  INTEGER
                       ACCESS  read-only
                       STATUS  mandatory
                       DESCRIPTION
                       "The blade's physical port number for the given entry."
                       ::= { bladeIPv6AddressEntry 2 }

           bladeIPv6AddressEntryIndex OBJECT-TYPE
                       SYNTAX  INTEGER
                       ACCESS  read-only
                       STATUS  mandatory
                       DESCRIPTION
                       "The blade's address entry index."
                       ::= { bladeIPv6AddressEntry 3 }

           bladeIPv6AddressType OBJECT-TYPE
                       SYNTAX  INTEGER 
                       { active-static(1), 
                         dhcp6(2), 
                         link-local(3),
                         autconfig(4),
                         current(5) }
                       ACCESS  read-only
                       STATUS  mandatory
                       DESCRIPTION
                       "The address type."
                       ::= { bladeIPv6AddressEntry 4 }

           bladeIPv6Address OBJECT-TYPE
                     SYNTAX  InetAddressIPv6
                     ACCESS  read-write
                     STATUS  mandatory
                     DESCRIPTION
                     "The assigned IPv6 address.
                     Note: 'write' is for static ipv6 only."
                     ::= { bladeIPv6AddressEntry 5 }

           bladeIPv6AddressPrefixLen OBJECT-TYPE
                       SYNTAX  INTEGER (1..128)
                       ACCESS  read-write
                       STATUS  mandatory
                       DESCRIPTION
                       "The prefix length for the given address.
                       Note: 'write' is for static ipv6 only."
                       ::= { bladeIPv6AddressEntry 6 }

           bladeIPv6AddressDefaultRoute OBJECT-TYPE
                     SYNTAX  InetAddressIPv6
                     ACCESS  read-write
                     STATUS  mandatory
                     DESCRIPTION
                     "The default route used for the given address.
                     Note: 'write' is for static ipv6 only."
                     ::= { bladeIPv6AddressEntry 7 }

         bladeSPEthOverUSBInterface OBJECT IDENTIFIER ::= { processorBlade 14 }

         spEthOverUSBInterfaceTable OBJECT-TYPE
                     SYNTAX  SEQUENCE OF SPEthOverUSBInterfaceEntry
                     ACCESS  not-accessible
                     STATUS  mandatory
                     DESCRIPTION
                     "Table of blade Service Processor's Ethernet over USB interface."
                     ::= { bladeSPEthOverUSBInterface 1 }

         spEthOverUSBInterfaceEntry OBJECT-TYPE
                    SYNTAX  SPEthOverUSBInterfaceEntry
                    ACCESS  not-accessible
                    STATUS  mandatory
                    DESCRIPTION
                    "Blade Service Processor's Ethernet over USB interface entry."
                    INDEX { spEthOverUSBInterfaceIndex }
                    ::= { spEthOverUSBInterfaceTable 1 }

         SPEthOverUSBInterfaceEntry ::= SEQUENCE {
                  spEthOverUSBInterfaceIndex INTEGER,
                  spEthOverUSBInterfaceBladeId OCTET STRING,
                  spEthOverUSBInterfaceBladeExists INTEGER,
                  spEthOverUSBInterfaceBladeName OCTET STRING,
                  spEthOverUSBInterfaceEnable INTEGER
                  }

         spEthOverUSBInterfaceIndex  OBJECT-TYPE
                  SYNTAX  INTEGER
                  ACCESS  read-only
                  STATUS  mandatory
                  DESCRIPTION
                  "Service Processor's Ethernet over USB interface table index."
                  ::= { spEthOverUSBInterfaceEntry 1 }

         spEthOverUSBInterfaceBladeId OBJECT-TYPE
                  SYNTAX  OCTET STRING
                  ACCESS  read-only
                  STATUS  mandatory
                  DESCRIPTION
                  "The numeric blade ID."
                  ::= { spEthOverUSBInterfaceEntry 2 }

         spEthOverUSBInterfaceBladeExists OBJECT-TYPE
                  SYNTAX  INTEGER {
                    false(0),
                    true(1)
                  }
                  ACCESS  read-only
                  STATUS  mandatory
                  DESCRIPTION
                  "Indicates whether the blade specified exists or not."
                  ::= { spEthOverUSBInterfaceEntry 3 }

         spEthOverUSBInterfaceBladeName OBJECT-TYPE
                  SYNTAX  OCTET STRING
                  ACCESS  read-only
                  STATUS  mandatory
                  DESCRIPTION
                  "The name of the blade as a null terminated string."
                  ::= { spEthOverUSBInterfaceEntry 6 }

         spEthOverUSBInterfaceEnable OBJECT-TYPE
                  SYNTAX  INTEGER {
                    disabled(0),
                    enabled(1),
                    notApplicable(255)
                  }
                  ACCESS  read-write
                  STATUS  mandatory
                  DESCRIPTION
                  "This object allows the user to view the status of, and enable
                  or disable, a blade Service Processor's command interface on
                  Ethernet-over-USB.

                  NOTE: If the blade either does not exist or does not support
                  Ethernet-over-USB command interface. It displays 'notApplicable'.
                  NOTE: It will take about 10 or more seconds for the disable/enable
                  setting to take effect."
                  ::= { spEthOverUSBInterfaceEntry 9 }

      -- ********************************************************************************
      -- Blade boot Device Info
      -- ********************************************************************************
      bootDeviceInfoTable OBJECT-TYPE
                     SYNTAX  SEQUENCE OF BootDeviceInfoEntry
                     ACCESS  not-accessible
                     STATUS  mandatory
                     DESCRIPTION
                     "Table of blade boot device information.  Contains
                     info for the boot devices for each blade."
                     ::= { processorBlade 15 }

       bootDeviceInfoEntry OBJECT-TYPE
                     SYNTAX BootDeviceInfoEntry
                     ACCESS  not-accessible
                     STATUS  mandatory
                     DESCRIPTION
                     "Boot device entry"
                     INDEX { bootInfoTopologyIndex, bootDeviceIndex }
                     ::= { bootDeviceInfoTable 1 }


       BootDeviceInfoEntry ::= SEQUENCE {
                   bootInfoTopologyIndex OCTET STRING,
                   bootDeviceIndex INTEGER,
                   bootDeviceId OCTET STRING,
                   bootDeviceActive INTEGER,
                   bootDevicePresence INTEGER,
                   bootDeviceLabel OCTET STRING,
                   bootDeviceUserLabel OCTET STRING,
                   bootDeviceOrder INTEGER
       }

       bootInfoTopologyIndex  OBJECT-TYPE
                   SYNTAX  OCTET STRING (SIZE (0..100))
                   ACCESS  read-only
                   STATUS  mandatory
                   DESCRIPTION
                    "The unique identifier for a node containing boot devices in this table. The chassis and each
                   installed component is represented by a hardware topology tree, where
                   each node in the tree represents a component. The path to a particular
                   component consists of one or more <component>,<instance> pairs, where
                   each successive pair is a child of the previous parent pair.

                   As an example, the root of the tree is the chassis and is represented
                   by the pair 'CHASSIS, 1'. This pair indicates the first instance of
                   the chassis. If a blade is inserted in slot 4 of the chassis, its
                   topology path is 'CHASSIS, 1, BLADE, 4'. With this format, the
                   components in the chassis can be determined along with their relative
                   hierarchy to each other.

                   This component inventory table is indexed by this unique topology
                   path and the relevant numeric designations for the components are:

                    CHASSIS,                0x01   Chassis
                    MM,                     0x02   Management Module
                    BLADE,                  0x03   Main system board of a blade"
                   ::= { bootDeviceInfoEntry 1 }


       bootDeviceIndex   OBJECT-TYPE
                   SYNTAX  INTEGER(0..255)
                   ACCESS  read-only
                   STATUS  mandatory
                   DESCRIPTION
                   "An index for the boot device for the given topology id."
                   ::= { bootDeviceInfoEntry 2 }

       bootDeviceId OBJECT-TYPE
                   SYNTAX  OCTET STRING
                   ACCESS  read-only
                   STATUS  mandatory
                   DESCRIPTION
                   "The device Id of the boot device."
                   ::= { bootDeviceInfoEntry 3 }

       bootDeviceActive   OBJECT-TYPE
                   SYNTAX  INTEGER {
                             no(0),
                             yes(1)
                           }
                   ACCESS  read-only
                   STATUS  mandatory
                   DESCRIPTION
                   "Specifies whether the boot device is active."
                   ::= { bootDeviceInfoEntry 4 }

       bootDevicePresence   OBJECT-TYPE
                   SYNTAX  INTEGER {
                             no(0),
                             yes(1)
                           }
                   ACCESS  read-only
                   STATUS  mandatory
                   DESCRIPTION
                   "Specifies whether the boot device is present."
                   ::= { bootDeviceInfoEntry 5 }

       bootDeviceLabel OBJECT-TYPE
                   SYNTAX  OCTET STRING
                   ACCESS  read-only
                   STATUS  mandatory
                   DESCRIPTION
                   "The device label of the boot device."
                   ::= { bootDeviceInfoEntry 6 }

        bootDeviceUserLabel OBJECT-TYPE
                   SYNTAX  OCTET STRING
                   ACCESS  read-only
                   STATUS  mandatory
                   DESCRIPTION
                   "The user label of the boot device."
                   ::= { bootDeviceInfoEntry 7 }

        bootDeviceOrder   OBJECT-TYPE
                   SYNTAX  INTEGER(0..255)
                   ACCESS  read-only
                   STATUS  mandatory
                   DESCRIPTION
                   "The sequence number in boot order of the boot device.
                   0 specifies this device is not in the boot sequence."
                   ::= { bootDeviceInfoEntry 8 }


      -- ********************************************************************************
      -- Blade boot sequence Info
      -- ********************************************************************************
         bootSequenceInfoTable OBJECT-TYPE
                     SYNTAX  SEQUENCE OF BootSequenceInfoEntry
                     ACCESS  not-accessible
                     STATUS  mandatory
                     DESCRIPTION
                     "Table of blade boot sequence information.  Contains
                     the boot sequence information for each blade."
                     ::= { processorBlade 16 }

       bootSequenceInfoEntry OBJECT-TYPE
                     SYNTAX BootSequenceInfoEntry
                     ACCESS  not-accessible
                     STATUS  mandatory
                     DESCRIPTION
                     "Boot sequence entry"
                     INDEX { bootSequenceInfoTopologyIndex }
                     ::= { bootSequenceInfoTable 1 }


       BootSequenceInfoEntry ::= SEQUENCE {
                   bootSequenceInfoTopologyIndex OCTET STRING,
                   bootSequenceInfoMaxBootDevices INTEGER,
                   bootSequenceInfoBootSequence OCTET STRING
       }

       bootSequenceInfoTopologyIndex  OBJECT-TYPE
                   SYNTAX  OCTET STRING (SIZE (0..100))
                   ACCESS  read-only
                   STATUS  mandatory
                   DESCRIPTION
                    "The unique identifier for a row in this table. The chassis and each
                   installed component is represented by a hardware topology tree, where
                   each node in the tree represents a component. The path to a particular
                   component consists of one or more <component>,<instance> pairs, where
                   each successive pair is a child of the previous parent pair.

                   As an example, the root of the tree is the chassis and is represented
                   by the pair 'CHASSIS, 1'. This pair indicates the first instance of
                   the chassis. If a blade is inserted in slot 4 of the chassis, its
                   topology path is 'CHASSIS, 1, BLADE, 4'. With this format, the
                   components in the chassis can be determined along with their relative
                   hierarchy to each other.

                   This component inventory table is indexed by this unique topology
                   path and the relevant numeric designations for the components are:

                    CHASSIS,                0x01   Chassis
                    MM,                     0x02   Management Module
                    BLADE,                  0x03   Main system board of a blade"
                   ::= { bootSequenceInfoEntry 1 }

       bootSequenceInfoMaxBootDevices   OBJECT-TYPE
                   SYNTAX  INTEGER(0..255)
                   ACCESS  read-only
                   STATUS  mandatory
                   DESCRIPTION
                   "The maximum number of boot devices."
                   ::= { bootSequenceInfoEntry 2 }

       bootSequenceInfoBootSequence OBJECT-TYPE
                   SYNTAX  OCTET STRING
                   ACCESS  read-write
                   STATUS  mandatory
                   DESCRIPTION
                   "A blank delimited string of device ids in the order of the boot sequence.
                   For example, 00000001 00000002 00000005. Note that the boot sequence list
                   can change from a given order and can grow from a given order, but cannot
                   be reduced in length. For example, if the sequence starts as 00000001 00000011,
                   it could change to 00000001 00000014 or grow to 00000001 00000014 00000002. In the 
                   example above, if the 00000002 selection was no longer desired, the list should be 
                   changed to 00000001 00000014 00000014, essentially repeating the last device ID.
                   Device ids must be listed in bootDeviceInfoTable."
                   ::= { bootSequenceInfoEntry 3 }

      -- ********************************************************************************
      -- Switch module control and config
      -- ********************************************************************************
      switchModule OBJECT IDENTIFIER ::= { components 3 }
       -- Server blade switch module control and configuration

       -- ********************************************************************************
       -- Switch module control
       -- ********************************************************************************
       switchModuleControl OBJECT IDENTIFIER ::= { switchModule 1 }
        -- Server blade switch module control

        smControlTable OBJECT-TYPE
                    SYNTAX  SEQUENCE OF SmControlEntry
                    ACCESS  not-accessible
                    STATUS  mandatory
                    DESCRIPTION
                    "Switch module control table."
                    ::= { switchModuleControl 1 }

         smControlEntry  OBJECT-TYPE
                       SYNTAX SmControlEntry
                       ACCESS  not-accessible
                       STATUS  mandatory
                       DESCRIPTION
                       "Switch module control table entry"
                       INDEX { smControlIndex }
                       ::= { smControlTable 1 }

         SmControlEntry ::= SEQUENCE {
                     smControlIndex INTEGER,
                     switchModuleControlId INTEGER,
                     smPostResultsAvailable INTEGER,
                     smPostResultsValue OCTET STRING,
                     switchModuleMemDiagEnableDisable INTEGER,
                     smCfgCtrlEnableDisable INTEGER,
                     smExtEthPortsEnableDisable INTEGER,
                     smCfgCtrlOnResetEnableDisable INTEGER,
                     smHealthState INTEGER,
                     smPMState INTEGER,
                     smPMCtrlEnableDisable INTEGER,
                     smIOCompatibility OCTET STRING
                     }

         smControlIndex OBJECT-TYPE
                     SYNTAX  INTEGER
                     ACCESS  read-only
                     STATUS  mandatory
                     DESCRIPTION
                     "Switch module control table index."
                     ::= { smControlEntry 1 }

         switchModuleControlId OBJECT-TYPE
                     SYNTAX  INTEGER {
                       module1(1),
                       module2(2),
                       module3(3),
                       module4(4),
                       module5(5),
                       module6(6),
                       module7(7),
                       module8(8),
                       module9(9),
                       module10(10)
                     }
                     ACCESS  read-only
                     STATUS  mandatory
                     DESCRIPTION
                     "The switch module numeric identifier."
                     ::= { smControlEntry 2 }

         smPostResultsAvailable OBJECT-TYPE
                     SYNTAX  INTEGER {
                       false(0),
                       true(1)
                     }
                     ACCESS  read-only
                     STATUS  mandatory
                     DESCRIPTION
                     "Describes whether the switch module POST diagnostic result
                     value contained in the smPostResultsValue is valid."
                     ::= { smControlEntry 3 }

         smPostResultsValue OBJECT-TYPE
                     SYNTAX  OCTET STRING
                     ACCESS  read-only
                     STATUS  mandatory
                     DESCRIPTION
                     "The range of values and meanings are as follows:
                      0x00 - 0x7F  (  0 - 127)  Base internal functions
                      0x80 - 0x9F  (128 - 159)  Internal interface failures
                      0xA0 - 0xAF  (160 - 175)  External interface failures
                      0xB0 - 0xFE  (176 - 254)  Reserved
                      0xFF         (255)        Switch completed POST successfully"
                     ::= { smControlEntry 4 }

         switchModuleMemDiagEnableDisable OBJECT-TYPE
                     SYNTAX  INTEGER {
                       enabled(0),
                       disabled(1)
                     }
                     ACCESS  read-write
                     STATUS  deprecated
                     DESCRIPTION
                     "Switch module memory diagnostics enabled or disabled.

                      NOTE: The numeric values for the enumerations for enabled and disabled are non-traditional
                            (i.e. - 0 and 1 are swapped), however, they cannot be changed since this MIB is already
                            published.  "
                     ::= { smControlEntry 5 }

         smCfgCtrlEnableDisable OBJECT-TYPE
                     SYNTAX  INTEGER {
                       disabled(0),
                       enabled(1)
                     }
                     ACCESS  read-write
                     STATUS  mandatory
                     DESCRIPTION
                     "Switch module configuration control.  When set to enabled, only the MM can manage
                     the module.
                     This MIB object can not be set, if MM grants switch module the Protected Mode permission.
                     This MIB object can not be set, if the switch module is participating in the Stacking Mode
                     and external management is protected.

                     NOTE: This MIB object is not applicable to modules that are running in Network Address
                            Translation (NAT) Mode. A value of disabled(0) will be returned."
                     ::= { smControlEntry 6 }

         smExtEthPortsEnableDisable OBJECT-TYPE
                     SYNTAX  INTEGER {
                       disabled(0),
                       enabled(1)
                     }
                     ACCESS  read-write
                     STATUS  mandatory
                     DESCRIPTION
                     "Switch module data (non-management) ethernet ports enabled or disabled.
                      This MIB object can not be set, if MM grants switch module the
                      Protected Mode permission.
                      This MIB object can not be set, if the switch module is participating
                      in the Stacking Mode and External Port Access is protected."
                     ::= { smControlEntry 7 }

         smCfgCtrlOnResetEnableDisable OBJECT-TYPE
                     SYNTAX  INTEGER {
                       enabled(0),
                       disabled(1)
                     }
                     ACCESS  read-write
                     STATUS  mandatory
                     DESCRIPTION
                     "Switch module configuration control on resets (default and unsolicited).
                     When set to enabled, the factory default IP configuration will become
                     active when the I/O module is reset to factory defaults by either the
                     management module or the I/O module. If an I/O module reset is initiated
                     by a source other than the management module then the previous IP configuration
                     will be in affect. In both these cases the MM will lose IP communications with
                     the IOM.
                     This MIB object can not be set, if MM grants switch module the Protected Mode
                     permission and switch module goes into Protected Mode.

                      NOTE: The numeric values for the enumerations for enabled and disabled are non-traditional
                            (i.e. - 0 and 1 are swapped), however, they cannot be changed since this MIB is already
                            published.

                     NOTE: This MIB object is not applicable to modules that are running in Network Address
                            Translation (NAT) Mode. A value of disabled(1) will be returned."
                     ::= { smControlEntry 9 }

         smHealthState OBJECT-TYPE
                     SYNTAX  INTEGER {
                       unknown(0),
                       good(1),
                       warning(2),
                       bad(3)
                     }
                     ACCESS  read-only
                     STATUS  mandatory
                     DESCRIPTION
                     "The health state for the switch module.
                     0 = unknown, 1 = good, 2 = warning, 3 = bad."
                     ::= { smControlEntry 15}

        smPMState OBJECT-TYPE
                     SYNTAX  INTEGER {
                       disabled(0),
                       pending(1),
                       attention(2),
                       active(3),
                       notApplicable(255)
                     }
                     ACCESS  read-only
                     STATUS  mandatory
                     DESCRIPTION
                     "The Protected Mode Status for the switch module.
                     standby- Protected Mode capability exists on the IOM but has not
                     been activated on the switch module or the MM.
                     pending - Protected Mode has been activated on the MM but not yet on the switch module.
                     active - Protected Mode is active on both the switch module and the MM.
                     attention - Protected Mode is enabled on the switch module but not on the MM."
                     ::= { smControlEntry 16}

        smPMCtrlEnableDisable OBJECT-TYPE
                     SYNTAX  INTEGER {
                       disabled(0),
                       enabled(1)
                     }
                     ACCESS  read-write
                     STATUS  mandatory
                     DESCRIPTION
                     "MM Protected Mode permission for the switch module.
                     disabled - allow MM to disable Protected Mode Permission for the switch module.
                     enabled - allow MM to grant Protected Mode Permission for the switch module."
                     ::= { smControlEntry 17}

        smIOCompatibility OBJECT-TYPE
                     SYNTAX  OCTET STRING
                     ACCESS  read-only
                     STATUS  mandatory
                     DESCRIPTION
                     "The compatibility status for the I/O module. This represents the 
                     worst case status for all of the internal network connections that this switch 
                     has to all of the blades in the chassis. For an equivalent view of this in the web, 
                     view the Chassis Management->I/O Modules menu item and select an switch from the 
                     name link under the Device Name column. From here, select the IO Connectivity tab
                     and the compatibility status for each with be shown.

                     The possible values and their meanings are as follows:

                     Unknown: This indicates a communication error for the I/O module.

                     OK: This is the normal (good) case where there are no compatibility
                     issues between the I/O module and the blades it is internally wired to.

                     No Fabric: This means the other end is not populated on any of the
                     blades this I/O module is internally wired to (e.g. this is an
                     Infiniband switch but none of the blades it is internally wired to
                     has an expansion card attached in the corresponding expansion slot).

                     Attention: Indicates one of the following cases:
                        One or more of the blades this I/O module is internally wired to is in communication error
                        The I/O module is powered off and at least one blade it is internally wired to is powered on

                     Mismatch: Indicates one of the following cases:
                        Fabric types are incompatible
                        An unknown I/O module type
                        An unknown fabric type on a blade the I/O module is internally wired to."
                     ::= { smControlEntry 18}

        smPingTable OBJECT-TYPE
                    SYNTAX  SEQUENCE OF SmPingEntry
                    ACCESS  not-accessible
                    STATUS  mandatory
                    DESCRIPTION

                    "Allows pinging one of the active assigned addresses of an I/O module.

                    NOTE: This table is not applicable to modules that are running in
                    Stacking Mode and IP configuration is protected."
                    ::= { switchModuleControl 2 }

         smPingEntry  OBJECT-TYPE
                       SYNTAX SmPingEntry
                       ACCESS  not-accessible
                       STATUS  mandatory
                       DESCRIPTION
                       "Represents a single address that can be pinged"
                       INDEX { smPingIndex, smPingAddressEntryIndex }
                       ::= { smPingTable 1 }

         SmPingEntry ::= SEQUENCE {
                     smPingIndex             INTEGER,
                     smPingAddressEntryIndex INTEGER,
                     smPingAddress           OCTET STRING,
                     smPingAddressExecute    INTEGER
                     }

         smPingIndex OBJECT-TYPE
                       SYNTAX  INTEGER
                       ACCESS  read-only
                       STATUS  mandatory
                       DESCRIPTION
                       "The switch module's slot number"
                       ::= { smPingEntry 1 }

         smPingAddressEntryIndex OBJECT-TYPE
                       SYNTAX  INTEGER
                       ACCESS  read-only
                       STATUS  mandatory
                       DESCRIPTION
                       "The switch module's address entry index"
                       ::= { smPingEntry 2 }

         smPingAddress OBJECT-TYPE
                       SYNTAX  OCTET STRING
                       ACCESS  read-only
                       STATUS  mandatory
                       DESCRIPTION
                       "The switch module's IPv4 or IPv6 address"
                       ::= { smPingEntry 3 }

         smPingAddressExecute OBJECT-TYPE
                       SYNTAX  INTEGER { execute(1) }
                       ACCESS  read-write
                       STATUS  mandatory
                       DESCRIPTION
                       "Pings the given IP address.

                       NOTE: The GET operation for this object is meaningless."
                       ::= { smPingEntry 4 }

        smPowerRestartTable OBJECT-TYPE
                    SYNTAX  SEQUENCE OF SmPowerRestartEntry
                    ACCESS  not-accessible
                    STATUS  mandatory
                    DESCRIPTION
                    "Switch module power restart table."
                    ::= { switchModuleControl 7 }

         smPowerRestartEntry  OBJECT-TYPE
                       SYNTAX SmPowerRestartEntry
                       ACCESS  not-accessible
                       STATUS  mandatory
                       DESCRIPTION
                       "Switch module power restart table entry"
                       INDEX { smPowerRestartIndex }
                       ::= { smPowerRestartTable 1 }

         SmPowerRestartEntry ::= SEQUENCE {
                     smPowerRestartIndex INTEGER,
                     smPowerRestartId INTEGER,
                     smSwitchExists INTEGER,
                     smMACAddress OCTET STRING,
                     smIPAddress IpAddress,
                     switchModulePowerOnOff INTEGER,
                     smReset INTEGER,
                     smResetToDefault INTEGER,
                     smRestartAndRunStdDiag INTEGER,
                     smRestartAndRunExtDiag INTEGER,
                     smRestartAndRunFullDiag INTEGER,
                     smPowerOnRestartDelay INTEGER,
                     smSwitchWidth INTEGER,
                     smManufacturingID OCTET STRING,
                     smStackingModeState INTEGER,
                     smStackingModeInfo OCTET STRING,
                     smManagementNetworkStatus INTEGER
                     }

         smPowerRestartIndex OBJECT-TYPE
                     SYNTAX  INTEGER
                     ACCESS  read-only
                     STATUS  mandatory
                     DESCRIPTION
                     "Switch module power restart index."
                     ::= { smPowerRestartEntry 1 }

         smPowerRestartId OBJECT-TYPE
                     SYNTAX  INTEGER {
                       module1(1),
                       module2(2),
                       module3(3),
                       module4(4),
                       module5(5),
                       module6(6),
                       module7(7),
                       module8(8),
                       module9(9),
                       module10(10)
                     }
                     ACCESS  read-only
                     STATUS  mandatory
                     DESCRIPTION
                     "The switch module numeric identifier."
                     ::= { smPowerRestartEntry 2 }

         smSwitchExists OBJECT-TYPE
                     SYNTAX  INTEGER {
                       false(0),
                       true(1)
                     }
                     ACCESS  read-only
                     STATUS  mandatory
                     DESCRIPTION
                     "Indicates whether the switch module specified exists or not."
                     ::= { smPowerRestartEntry 3 }

         smMACAddress OBJECT-TYPE
                     SYNTAX  OCTET STRING
                     ACCESS  read-only
                     STATUS  mandatory
                     DESCRIPTION
                     "Switch module MAC address.

                      For IOMs which are members of a stack, this field is not applicable and should be disregarded."
                     ::= { smPowerRestartEntry 5 }

         smIPAddress OBJECT-TYPE
                     SYNTAX  IpAddress
                     ACCESS  read-only
                     STATUS  mandatory
                     DESCRIPTION
                     "The switch module current IP address.
                     If the switch module is participating in the Stacking Mode
                     and IP Configuration is protected, then the stack management
                     IP address is displayed.

                     NOTE: IPv6 addresses for the switch can be view with the
                     smIPv6AddressTable."
                     ::= { smPowerRestartEntry 6 }

         switchModulePowerOnOff OBJECT-TYPE
                     SYNTAX  INTEGER {
                       poweroff(0),
                       poweron(1),
                       shutdownInProgress(2)
                     }
                     ACCESS  read-write
                     STATUS  mandatory
                     DESCRIPTION
                     "I/O Module power on or power off.  If powering on a currently
                     powered off I/O Module, then the I/O Module will execute a POST.
                     The results of this POST will need to be retrieved using the 'Post Results'
                     command.
                     NOTE:
                     When powering off a currently powered on I/O Module, a minimum of 1 second
                     is needed to allow the module to power off before powering back on.
                     The value 'shutdownInProgress' is for I/O Modules that may take some time to
                     transition from 'poweron' to 'poweroff'.  
                     This MIB object can not be set, if MM grants the I/O Module the Protected Mode
                     permission and module goes into Protected Mode."
                     ::= { smPowerRestartEntry 7 }

         smReset OBJECT-TYPE
                     SYNTAX  INTEGER {
                       execute(1)
                     }
                     ACCESS  read-write
                     STATUS  mandatory
                     DESCRIPTION
                     "For the case where the switch module is currently powered on, this command
                     will effectively power off and then power on the switch module indicated and
                     cause it to run its POST test.  For the case where the switch module is
                     currently powered off, the command will just power on the switch module.
                     This MIB object can not be set, if MM grants switch module the Protected Mode
                     permission and switch module goes into Protected Mode.
                     NOTE: Value returned for the GET command is meaningless for this MIB object."
                     ::= { smPowerRestartEntry 8 }

         smResetToDefault OBJECT-TYPE
                     SYNTAX  INTEGER {
                       execute(1)
                     }
                     ACCESS  read-write
                     STATUS  mandatory
                     DESCRIPTION
                     "For the case where the switch module is currently powered on, this command
                     will effectively power off and then power on the switch module indicated and
                     cause it to run its POST test.  For the case where the switch module is
                     currently powered off, the command will just power on the switch module.
                     In both cases, the switch module will reset the configuration to the default
                     values.
                     This MIB object can not be set, if MM grants switch module the Protected Mode
                     permission and switch module goes into Protected Mode.
                     This MIB object can not be set, if the switch module is participating in the
                     Stacking Mode and reset to default is protected.
                     NOTE: Value returned for the GET command is meaningless for this MIB object."
                     ::= { smPowerRestartEntry 9 }

         smRestartAndRunStdDiag OBJECT-TYPE
                     SYNTAX  INTEGER {
                       execute(1)
                     }
                     ACCESS  read-write
                     STATUS  mandatory
                     DESCRIPTION
                     "To power cycle the selected module(s) and then run the standard diagnostic
                     test package.

                     NOTE: Value returned for the GET command is meaningless for this MIB object."
                     ::= { smPowerRestartEntry 10 }

         smRestartAndRunExtDiag OBJECT-TYPE
                     SYNTAX  INTEGER {
                       execute(1)
                     }
                     ACCESS  read-write
                     STATUS  mandatory
                     DESCRIPTION
                     "To power cycle the selected module(s) and then run the extended diagnostic
                     test package. This option is not supported on all I/O modules.

                     NOTE: Value returned for the GET command is meaningless for this MIB object."
                     ::= { smPowerRestartEntry 11 }

         smRestartAndRunFullDiag OBJECT-TYPE
                     SYNTAX  INTEGER {
                       execute(1)
                     }
                     ACCESS  read-write
                     STATUS  mandatory
                     DESCRIPTION
                     "To power cycle the selected module(s) and then run the full diagnostic test
                     package. The full diagnostic test package may take over 5 minutes to run.
                     This option is not supported on all I/O modules.

                     NOTE: Value returned for the GET command is meaningless for this MIB object."
                     ::= { smPowerRestartEntry 12 }

         smPowerOnRestartDelay OBJECT-TYPE
                     SYNTAX  INTEGER (0..32767)
                     ACCESS  read-write
                     STATUS  mandatory
                     DESCRIPTION
                     "Restart delay (in seconds) when power is applied to a switch module."
                     ::= { smPowerRestartEntry 15 }

         smSwitchWidth OBJECT-TYPE
                     SYNTAX  INTEGER
                     ACCESS  read-only
                     STATUS  mandatory
                     DESCRIPTION
                     "Switch module width."
                     ::= { smPowerRestartEntry 21 }

        smManufacturingID OBJECT-TYPE
                      SYNTAX  OCTET STRING
                      ACCESS  read-only
                      STATUS  mandatory
                      DESCRIPTION
                      "Switch module hardware VPD manufacturing ID."
                      ::= { smPowerRestartEntry 22 }

        smStackingModeState OBJECT-TYPE
                     SYNTAX  INTEGER {
                       standby(0),
                       member(1),
                       master(2),
                       notApplicable(255)
                     }
                     ACCESS  read-only
                     STATUS  mandatory
                     DESCRIPTION
                     "The Stacking Mode Status for the switch module.
                     standby - I/O module has stacking capability but is not part of a stack.
                     member - I/O module has stacking capability and is part of a stack in the
                       member role.
                     master - I/O module has stacking capability and is part of a stack in the
                       master role.
                     NOTE: The term disabled was changed to the term standby to be more descriptive."
                     ::= { smPowerRestartEntry 23 }

        smStackingModeInfo OBJECT-TYPE
                    SYNTAX OCTET STRING
                    ACCESS read-only
                    STATUS mandatory
                    DESCRIPTION
                    "A string containing a text description about the details of which functions are
                    protected for a switch module when it is in Stacking Mode as Master or Member.
                    The possible functions protected by switch modules are IP configuration,
                    External Port Access, External Management all over ports and Restore to defaults."
                    ::= { smPowerRestartEntry 24 }

         smManagementNetworkStatus OBJECT-TYPE
                     SYNTAX  INTEGER {
                       off(0),
                       on(1)
                     }
                     ACCESS  read-only
                     STATUS  mandatory
                     DESCRIPTION
                     "Displays the management network interface status.  For IOMs which are members
                     of a stack,  this field is not applicable and should be disregarded."
                     ::= { smPowerRestartEntry 25 }


       smIOCompatibilityTable OBJECT-TYPE
                   SYNTAX  SEQUENCE OF SmIOCompatibilityEntry
                   ACCESS  not-accessible
                   STATUS  mandatory
                   DESCRIPTION
                   "Switch module I/O  compatibility table. This table will show for each IOM
                   a set of rows corresponding to the internal connections the IOM has to each 
                   node in the chassis."
                   ::= { switchModuleControl 10 }

        smIOCompatibilityEntry  OBJECT-TYPE
                      SYNTAX SmIOCompatibilityEntry
                      ACCESS  not-accessible
                      STATUS  mandatory
                      DESCRIPTION
                      "Switch module IO compatibility table entry"
                      INDEX { smIOCompatibilityIndex }
                      ::= { smIOCompatibilityTable 1 }

        SmIOCompatibilityEntry ::= SEQUENCE {
                    smIOCompatibilityIndex INTEGER,
                    smIOCompatibilityId INTEGER,
                    smIOCompatibilityModuleBay OCTET STRING,
                    smIOCompatibilityModulePower OCTET STRING,
                    smIOCompatibilityModuleFabricType OCTET STRING,
                    smIOCompatibilityStatus OCTET STRING,
                    smIOCompatibilityTargetTopologyPath OCTET STRING
                    }

        smIOCompatibilityIndex OBJECT-TYPE
                    SYNTAX  INTEGER
                    ACCESS  read-only
                    STATUS  mandatory
                    DESCRIPTION
                    "Switch module IO compatibility index. Just an incrementing number."
                    ::= { smIOCompatibilityEntry 1 }

        smIOCompatibilityId OBJECT-TYPE
                    SYNTAX  INTEGER {
                      module1(1),
                      module2(2),
                      module3(3),
                      module4(4),
                      module5(5),
                      module6(6),
                      module7(7),
                      module8(8),
                      module9(9),
                      module10(10)
                    }
                    ACCESS  read-only
                    STATUS  mandatory
                    DESCRIPTION
                    "The switch module numeric identifier. Basically indicating which 
                     slot the switch is installed in."
                    ::= { smIOCompatibilityEntry 2 }

        smIOCompatibilityModuleBay OBJECT-TYPE
                    SYNTAX  OCTET STRING
                    ACCESS  read-only
                    STATUS  deprecated
                    DESCRIPTION
                    "This object is deprecated because it is not applicable to the system.
                     Please refer to smIOCompatibilityTargetTopologyPath for module bay information."
                    ::= { smIOCompatibilityEntry 3 }

        smIOCompatibilityModulePower OBJECT-TYPE
                    SYNTAX  OCTET STRING
                    ACCESS  read-only
                    STATUS  mandatory
                    DESCRIPTION
                    "The power state of the IO module specified in smIOCompatibilityId."
                    ::= { smIOCompatibilityEntry 4 }

        smIOCompatibilityModuleFabricType OBJECT-TYPE
                    SYNTAX  OCTET STRING
                    ACCESS  read-only
                    STATUS  mandatory
                    DESCRIPTION
                    "The fabric type of the I/O module port.
                    'n/a' will be displayed if the corresponding channel is not populated
                    on the module side (e.g. we are looking at the details for an Infiniband
                    switch but the blade does not have an Infiniband expansion card attached
                    in the corresponding expansion slot)."
                    ::= { smIOCompatibilityEntry 5 }

        smIOCompatibilityStatus OBJECT-TYPE
                    SYNTAX  OCTET STRING
                    ACCESS  read-only
                    STATUS  mandatory
                    DESCRIPTION
                    "The compatibility status between the I/O module and the node specified
                    in smIOCompatibilityTargetTopologyPath object.

                    To see an equivalent representation in the web, go to the 
                    Chassis Management->I/O Modules menu item and select a switch from the
                    table by clicking on the name link under the Device Name column. From here,
                    select the IO Connectivity tab and you will see all of the blade network 
                    connecitons that this IOM has, along with the compatibility status in the 
                    last column.

                    The possible values are:

                    OK: No compatibility issues

                    No Fabric: Indicates the corresponding channel is not populated on the blade
                               side even though the blade is present (e.g. we are looking at the details
                               for an Infiniband switch but the blade specified in smIOCompatibilityTargetTopologyPath
                               does not have an Infiniband expansion card attached in the corresponding expansion slot).

                    Attention: Indicates one of the following:
                               The blade specified in smIOCompatibilityTargetTopologyPath has a communication error.
                               The I/O module is powered off but the blade specified in smIOCompatibilityTargetTopologyPath
                               is powered on.

                    Mismatch: Indicates one of the following cases::
                              Fabric types are incompatible
                              Unknown fabric type on the blade side
                              Unknown I/O module type"
                    ::= { smIOCompatibilityEntry 6 }

        smIOCompatibilityTargetTopologyPath  OBJECT-TYPE
                   SYNTAX  OCTET STRING  (SIZE (0..100))
                   ACCESS  read-only
                   STATUS  mandatory
                   DESCRIPTION
                   "The unique identifier for a node which communicates with this IO module.  
                    
                    The installed component is represented by a hardware topology tree, where
                    each node in the tree represents a component. The path to a particular
                    component consists of one or more <component>,<instance> pairs, where
                    each successive pair is a child of the previous parent pair.

                    As an example, the root of the tree is the chassis and is represented
                    by the pair 'CHASSIS, 1'. This pair indicates the first instance of
                    the chassis. If a blade is inserted in slot 4 of the chassis, its
                    topology path is 'CHASSIS, 1, BLADE, 4'. With this format, the
                    components in the chassis can be determined along with their relative
                    hierarchy to each other.

                    This component table is indexed by this unique topology
                    path and the numeric designations for the components are:

                     CHASSIS,                0x01   Chassis
                     MM,                     0x02   Management Module
                     BLADE,                  0x03   Main system board of a blade
                     POWER,                  0x04   Power Supply, Power Module, etc
                     COOLING,                0x05   Fan, blower, or other cooling device
                     IO_MODULE,              0x06   Has I/O interface, i.e. - switch or bridge
                     MEDIA,                  0x07   Media device
                     PROCESSOR,              0x08   Any processor, processor module, etc
                     STORAGE,                0x09   Any type of storage device
                     EXPANSION,              0x0A   Expansion Card (not covered by more specific type)
                     MEMORY,                 0x0B   Any memory device, module, etc
                     MFRU,                   0x0C   Managed FRU Device
                     PANEL,                  0x0D   Any sort of panel device, such as a front panel
                     BLADE_EXPANSION_MODULE, 0x0E   Expansion option (BEM) such as PEU, BSE, etc
                     CARD_EXPANSION,         0x0F   Expansion card, ie. daughter card
                     CARD_HS_EXPANSION,      0x10   High Speed Expansion card, ie. daughter card
                     INTERPOSER,             0x11   Interposer device
                     CLOCK,                  0x12   Clock card
                     MUX,                    0x13   Mulitplexer card
                     ADDIN,                  0x14   cKVM card & other addin cards
                     STORAGE_MODULE,         0x15   Container of one or more Storage Devices
                     SYS_EXPANSION_CARD,     0x16   Management card
                     BATTERY,                0x17   A single battery
                     BATTERY_MODULE,         0x18   Container of one or more batteries
                     REAR_LED,               0x19   Rear LED card
                     MEMORY_BANK,            0x1A   Memory banks
                     AIR_FILTER,             0x1B   Filter mechanism (bezel)
                     SERIAL_PORT_MODULE,     0x1C   Container of one or more serial ports
                     PARENT,                 0x1D   Reference to parent for multi-parent support
                     PHY_PORT,               0x1E   Physical port
                     IO_EXPANDER,            0x1F   RAID card
                     CABLE,                  0x20   Cable/Interconnect
                     FAN_MUX                 0x29   Fan multiplexer card
                     PCI_EXPRESS,            0x32   PCI express card on (PEN)
                     FLASH_DIMM,             0x33   Used for SPD devices that matches the silkscreen of the DIMM slot
                     RACK,                   0x50   Rack
                     PLATFORM,               0x51   Generic Platform like rack mounted server/appliance
                     DATAPLEX,               0x52   DataPlex
                     OTHER,                  0x53   Other unknown etc.
                     PERIPHERAL_MODULE,      0x54 
                     SYSTEM_BOARD,           0x55   System board
                     PROCESSOR_MODULE,       0x56 
                     BACK_PANEL,             0x57 
                     POWER_SYSTEM_BOARD,     0x58 
                     STORAGE_BACKPLANE,      0x59   Drive back plane
                     PROC_BOARD,             0x5A   Holds 1 or more processors
                     POWER_DI,               0x5B   Power mgt / power distribution board
                     CHASSIS_BACK_PANEL,     0x5C 
                     SUB_CHASSIS,            0x5D 
                     OTHER_CHASSIS_BOARD,    0x5E 
                     DEVICE_MODULE,          0x5F 
                     REMOTE_DEVICE,          0x60   Remote mgt communication device
                     EXTERNAL_ENVIRONMENT,   0x61   Such as external temp sensor for outside box temps
                     PROC_MEMORY_MODULE,     0x62   Processors and memory on same module"
                   ::= { smIOCompatibilityEntry 7 }


       -- ********************************************************************************
       -- Switch module config
       -- ********************************************************************************
       switchModuleConfig OBJECT IDENTIFIER ::= { switchModule 2 }
        -- Server blade switch module configuration

        switchMgmtNetworkCfg OBJECT IDENTIFIER ::= { switchModuleConfig 1 }
         -- Server blade switch module management network config

         --
         -- Current switch module network config
         --
         switchCurrentNwCfg OBJECT IDENTIFIER ::= { switchMgmtNetworkCfg 1 }
          -- Server blade switch module current network config

          smCurrentIPInfoTable OBJECT-TYPE
                      SYNTAX  SEQUENCE OF SmCurrentIPInfoEntry
                      ACCESS  not-accessible
                      STATUS  mandatory
                      DESCRIPTION
                      "Switch module current IP information.

                      NOTE: This MIB object is not applicable to modules that are running in
                      Stacking Mode and IP configuration is protected."
                      ::= { switchCurrentNwCfg 1 }

           smCurrentIPInfoEntry  OBJECT-TYPE
                         SYNTAX SmCurrentIPInfoEntry
                         ACCESS  not-accessible
                         STATUS  mandatory
                         DESCRIPTION
                         "Switch module current IP table entry.

                         NOTE: This MIB object is not applicable to modules that are running in
                         Stacking Mode and IP configuration is protected."
                         INDEX { smCurrentIPInfoIndex }
                         ::= { smCurrentIPInfoTable 1 }

           SmCurrentIPInfoEntry ::= SEQUENCE {
                       smCurrentIPInfoIndex INTEGER,
                       smCurrentIPInfoId INTEGER,
                       smCurrentIPInfoExists INTEGER,
                       smCurrentIPInfoPowerState INTEGER,
                       smCurrentIPAddr IpAddress,
                       smCurrentSubnetMask IpAddress,
                       smCurrentGateway IpAddress,
                       smCurrentIPConfigMethod INTEGER
                       }

           smCurrentIPInfoIndex OBJECT-TYPE
                       SYNTAX  INTEGER
                       ACCESS  read-only
                       STATUS  mandatory
                       DESCRIPTION
                       "Switch module current IP info index.

                        NOTE: This MIB object is not applicable to modules that are running in
                        Stacking Mode and IP configuration is protected."
                       ::= { smCurrentIPInfoEntry 1 }

           smCurrentIPInfoId OBJECT-TYPE
                       SYNTAX  INTEGER {
                         module1(1),
                         module2(2),
                         module3(3),
                         module4(4),
                         module5(5),
                         module6(6),
                         module7(7),
                         module8(8),
                         module9(9),
                         module10(10)
                       }
                       ACCESS  read-only
                       STATUS  mandatory
                       DESCRIPTION
                       "The switch module numeric identifier.

                        NOTE: This MIB object is not applicable to modules that are running in
                        Stacking Mode and IP configuration is protected."
                       ::= { smCurrentIPInfoEntry 2 }

           smCurrentIPInfoExists OBJECT-TYPE
                       SYNTAX  INTEGER {
                         false(0),
                         true(1)
                       }
                       ACCESS  read-only
                       STATUS  mandatory
                       DESCRIPTION
                       "Indicates whether the switch module specified exists or not.

                        NOTE: This MIB object is not applicable to modules that are running in
                        Stacking Mode and IP configuration is protected."
                       ::= { smCurrentIPInfoEntry 3 }

           smCurrentIPInfoPowerState OBJECT-TYPE
                       SYNTAX  INTEGER {
                         off(0),
                         on(1),
                         shutdownInProgress(2)
                       }
                       ACCESS  read-only
                       STATUS  mandatory
                       DESCRIPTION
                       "Indicates whether the I/O Module specified is powered on or not.
                        The value 'shutdownInProgress' is for the I/O Module that may take some time to
                        transition from 'poweron' to 'poweroff'. 

                        NOTE: This MIB object is not applicable to modules that are running in
                        Stacking Mode and IP configuration is protected."
                       ::= { smCurrentIPInfoEntry 4 }

           smCurrentIPAddr OBJECT-TYPE
                        SYNTAX  IpAddress
                        ACCESS  read-only
                        STATUS  mandatory
                        DESCRIPTION
                        "The switch module current IP address.

                         NOTE: This MIB object is not applicable to modules that are running in
                         Stacking Mode and IP configuration is protected."
                        ::= { smCurrentIPInfoEntry 6 }

           smCurrentSubnetMask OBJECT-TYPE
                        SYNTAX  IpAddress
                        ACCESS  read-only
                        STATUS  mandatory
                        DESCRIPTION
                        "The switch module current subnet mask.

                         NOTE: This MIB object is not applicable to modules that are running in
                         Stacking Mode and IP configuration is protected."
                        ::= { smCurrentIPInfoEntry 7 }

          smCurrentGateway OBJECT-TYPE
                       SYNTAX  IpAddress
                       ACCESS  read-only
                       STATUS  mandatory
                       DESCRIPTION
                       "The switch module current IP gateway.

                        NOTE: This MIB object is not applicable to modules that are running in
                        Stacking Mode and IP configuration is protected."
                       ::= { smCurrentIPInfoEntry 8 }

          smCurrentIPConfigMethod OBJECT-TYPE
                       SYNTAX  INTEGER {
                         unknown(0),
                         static(1),
                         dhcp(2),
                         nat (3),
                         bootp(4)
                       }
                       ACCESS  read-only
                       STATUS  mandatory
                       DESCRIPTION
                       "The switch module current IP configuration method.

                        NOTE: This MIB object is not applicable to modules that are running in
                        Stacking Mode and IP configuration is protected."
                       ::= { smCurrentIPInfoEntry 9 }

         -- ********************************************************************************
         -- New switch module network config
         -- ********************************************************************************
         switchNewNwCfg OBJECT IDENTIFIER ::= { switchMgmtNetworkCfg 2 }
          -- Server blade switch module new network config

          smNewIPInfoTable OBJECT-TYPE
                      SYNTAX  SEQUENCE OF SmNewIPInfoEntry
                      ACCESS  not-accessible
                      STATUS  mandatory
                      DESCRIPTION
                      "Switch module new IP information.

                       NOTE: This MIB object is not applicable to modules that are running in Network Address
                       Translation (NAT) Mode or Stacking Mode and IP configuration is protected."
                      ::= { switchNewNwCfg 1 }

           smNewIPInfoEntry  OBJECT-TYPE
                         SYNTAX SmNewIPInfoEntry
                         ACCESS  not-accessible
                         STATUS  mandatory
                         DESCRIPTION
                         "Switch module new IP configuration information table entry.

                         NOTE: This MIB table is not applicable to modules that are running in Network Address
                         Translation (NAT) Mode or Stacking Mode and IP configuration is protected."
                         INDEX { smNewIPInfoIndex }
                         ::= { smNewIPInfoTable 1 }

           SmNewIPInfoEntry ::= SEQUENCE {
                       smNewIPInfoIndex INTEGER,
                       smNewIPInfoId INTEGER,
                       smNewIPInfoExists INTEGER,
                       smNewIPInfoPowerState INTEGER,
                       smNewIPAddr IpAddress,
                       smNewSubnetMask IpAddress,
                       smNewGateway IpAddress,
                       smNewIPConfigMethod INTEGER,
                       smNewIPConfigEnableDisable INTEGER
                       }

           smNewIPInfoIndex OBJECT-TYPE
                       SYNTAX  INTEGER
                       ACCESS  read-only
                       STATUS  mandatory
                       DESCRIPTION
                       "Switch module new IP info index.

                       NOTE: This MIB object is not applicable to modules that are running in Network Address
                       Translation (NAT) Mode or Stacking Mode and IP configuration is protected."
                       ::= { smNewIPInfoEntry 1 }

           smNewIPInfoId OBJECT-TYPE
                       SYNTAX  INTEGER {
                         module1(1),
                         module2(2),
                         module3(3),
                         module4(4),
                         module5(5),
                         module6(6),
                         module7(7),
                         module8(8),
                         module9(9),
                         module10(10)
                       }
                       ACCESS  read-only
                       STATUS  mandatory
                       DESCRIPTION
                       "The switch module numeric identifier.

                       NOTE: This MIB object is not applicable to modules that are running in Network Address
                       Translation (NAT) Mode or Stacking Mode and IP configuration is protected."
                       ::= { smNewIPInfoEntry 2 }

           smNewIPInfoExists OBJECT-TYPE
                       SYNTAX  INTEGER {
                         false(0),
                         true(1)
                       }
                       ACCESS  read-only
                       STATUS  mandatory
                       DESCRIPTION
                       "Indicates whether the switch module specified exists or not.

                       NOTE: This MIB object is not applicable to modules that are running in Network Address
                       Translation (NAT) Mode or Stacking Mode and IP configuration is protected."
                       ::= { smNewIPInfoEntry 3 }

           smNewIPInfoPowerState OBJECT-TYPE
                       SYNTAX  INTEGER {
                         off(0),
                         on(1)
                       }
                       ACCESS  read-only
                       STATUS  mandatory
                       DESCRIPTION
                       "Indicates whether the switch module specified is powered on or not.

                       NOTE: This MIB object is not applicable to modules that are running in Network Address
                       Translation (NAT) Mode or Stacking Mode and IP configuration is protected.."
                       ::= { smNewIPInfoEntry 4 }

           smNewIPAddr OBJECT-TYPE
                        SYNTAX  IpAddress
                        ACCESS  read-write
                        STATUS  mandatory
                        DESCRIPTION
                        "The switch module new IP address.  Before setting this object to a new value,
                        smNewIpconfigEnableDisable object must first be set to disabled.
                        NOTE: This MIB object can not be set if the MM grants the switch module Protected Mode
                        permission and the switch module goes into Protected Mode.
                        NOTE: This MIB object can not be set if the switch module is in Stacking Mode
                        and IP Configuration is protected.
                        NOTE: This MIB object is not applicable to modules that are running in Network Address
                        Translation (NAT) Mode."
                        ::= { smNewIPInfoEntry 6 }

           smNewSubnetMask OBJECT-TYPE
                        SYNTAX  IpAddress
                        ACCESS  read-write
                        STATUS  mandatory
                        DESCRIPTION
                        "The switch module new subnet mask.  Before setting this object to a new value,
                        smNewIpconfigEnableDisable object must first be set to disabled.
                        NOTE: This MIB object can not be set if the MM grants the switch module Protected Mode
                        permission and the switch module goes into Protected Mode.
                        NOTE: This MIB object can not be set if the switch module is in Stacking Mode,
                        and IP Configuration is protected.
                        NOTE: This MIB object is not applicable to modules that are running in Network Address
                        Translation (NAT) Mode."
                        ::= { smNewIPInfoEntry 7 }

           smNewGateway OBJECT-TYPE
                        SYNTAX  IpAddress
                        ACCESS  read-write
                        STATUS  mandatory
                        DESCRIPTION
                        "The switch module new IP gateway.  Before setting this object to a new value,
                        smNewIpconfigEnableDisable object must first be set to disabled.
                        NOTE: This MIB object can not be set if the MM grants the switch module Protected Mode
                        permission and the switch module goes into Protected Mode.
                        NOTE: This MIB object can not be set if the switch module is in Stacking Mode,
                        and IP Configuration is protected.
                        NOTE: This MIB object is not applicable to modules that are running in Network Address
                        Translation (NAT) Mode."
                        ::= { smNewIPInfoEntry 8 }

           smNewIPConfigMethod OBJECT-TYPE
                        SYNTAX  INTEGER {
                          unknown(0),
                          static(1),
                          dhcp(2),
                          nat(3),
                          bootp(4)
                        }
                        ACCESS  read-write
                        STATUS  mandatory
                        DESCRIPTION
                        "The switch module new IP configuration method.  Before setting this object to a new value,
                        smNewIpconfigEnableDisable object must first be set to disabled.
                        NOTE: This MIB object can not be set if the MM grants the switch module Protected Mode
                        permission and the switch module goes into Protected Mode.
                        NOTE: This MIB object can not be set if the switch module is in Stacking Mode,
                        and IP Configuration is protected.
                        NOTE: This MIB object is not applicable to modules that are running in Network Address
                        Translation (NAT) Mode."
                        ::= { smNewIPInfoEntry 9 }

           smNewIPConfigEnableDisable OBJECT-TYPE
                       SYNTAX  INTEGER {
                         disable(0),
                         enable(1)
                       }
                       ACCESS  read-write
                       STATUS  mandatory
                       DESCRIPTION
                       "A set command enables a new IP configuration that has been
                       previously defined.  A get command indicates whether the new
                       IP configuration information has been enabled.
                       NOTE: This MIB object can not be set if the MM grants the switch module Protected Mode
                       permission and the switch module goes into Protected Mode.
                       NOTE: This MIB object can not be set if the switch module is in Stacking Mode,
                       and IP Configuration is protected.
                       NOTE: This MIB object is not applicable to modules that are running in Network Address
                       Translation (NAT) Mode."
                       ::= { smNewIPInfoEntry 10 }

         switchIPv6Config OBJECT IDENTIFIER ::= { switchMgmtNetworkCfg 4 }
          smIPv6ConfigTable OBJECT-TYPE
                      SYNTAX  SEQUENCE OF SmIPv6ConfigEntry
                      ACCESS  not-accessible
                      STATUS  mandatory
                      DESCRIPTION
                      "A table of IPv6 configuration options for switch modules.

                      NOTE: This MIB object is not applicable to modules that are running in
                      Stacking Mode and IP configuration is protected.

                      NOTE: This MIB object is not applicable to modules that
                      do not support IPv6."
                      ::= { switchIPv6Config 1 }

           smIPv6ConfigEntry  OBJECT-TYPE
                         SYNTAX SmIPv6ConfigEntry
                         ACCESS  not-accessible
                         STATUS  mandatory
                         DESCRIPTION
                         "IPv6 configuration options for a switch module..

                         NOTE: This MIB object is not applicable to modules that are running in
                         Stacking Mode and IP configuration is protected.

                         NOTE: This MIB object is not applicable to modules that
                         do not support IPv6."
                         INDEX { smIPv6ConfigIndex }
                         ::= { smIPv6ConfigTable 1 }

           SmIPv6ConfigEntry ::= SEQUENCE {
                       smIPv6ConfigIndex INTEGER,
                       smIPv6ConfigEnabled INTEGER,
                       smIPv6ConfigStatic INTEGER,
                       smDHCPv6ConfigEnabled INTEGER,
                       smIPv6ConfigStatelessEnabled INTEGER
                       }

           smIPv6ConfigIndex OBJECT-TYPE
                       SYNTAX  INTEGER
                       ACCESS  read-only
                       STATUS  mandatory
                       DESCRIPTION
                       "The switch module's slot number"
                       ::= { smIPv6ConfigEntry 1 }
           smIPv6ConfigEnabled OBJECT-TYPE
                       SYNTAX  INTEGER { enable(1) }
                       ACCESS  read-write
                       STATUS  mandatory
                       DESCRIPTION
                       "Enables/Disables IPv6 support on the switch module."
                       ::= { smIPv6ConfigEntry 2 }
           smIPv6ConfigStatic OBJECT-TYPE
                       SYNTAX  INTEGER { disable(0),enable(1) }
                       ACCESS  read-write
                       STATUS  mandatory
                       DESCRIPTION
                       "Enables/Disables IPv6 static configuration support on the switch module."
                       ::= { smIPv6ConfigEntry 3 }
           smDHCPv6ConfigEnabled OBJECT-TYPE
                       SYNTAX  INTEGER { disable(0),enable(1) }
                       ACCESS  read-write
                       STATUS  mandatory
                       DESCRIPTION
                       "Enables/Disables DHCPv6 address configuration support on the switch module."
                       ::= { smIPv6ConfigEntry 4 }
           smIPv6ConfigStatelessEnabled OBJECT-TYPE
                       SYNTAX  INTEGER { disable(0),enable(1) }
                       ACCESS  read-write
                       STATUS  mandatory
                       DESCRIPTION
                       "Enables/Disables IPv6 stateless auto-configuration support on the switch module."
                       ::= { smIPv6ConfigEntry 5 }

          smIPv6AddressTable OBJECT-TYPE
                      SYNTAX  SEQUENCE OF SmIPv6AddressEntry
                      ACCESS  not-accessible
                      STATUS  mandatory
                      DESCRIPTION
                      "A table of assigned IPv6 addresses for switch modules.

                      NOTE: This MIB object is not applicable to modules that are running in
                      Stacking Mode and IP configuration is protected.

                      NOTE: This MIB object is not applicable to modules that
                      do not support IPv6."
                      ::= { switchIPv6Config 2 }

           smIPv6AddressEntry  OBJECT-TYPE
                         SYNTAX SmIPv6AddressEntry
                         ACCESS  not-accessible
                         STATUS  mandatory
                         DESCRIPTION
                         "The assigned IPv6 address for a given switch module

                         NOTE: This MIB object is not applicable to modules that are running in
                         Stacking Mode and IP configuration is protected.

                         NOTE: This MIB object is not applicable to modules that
                         do not support IPv6."
                         INDEX { smIPv6AddressIndex, smIPv6AddressEntryIndex}
                         ::= { smIPv6AddressTable 1 }

           SmIPv6AddressEntry ::= SEQUENCE {
                       smIPv6AddressIndex          INTEGER,
                       smIPv6AddressEntryIndex     INTEGER,
                       smIPv6AddressType           INTEGER,
                       smIPv6Address               InetAddressIPv6,
                       smIPv6AddressPrefixLen      INTEGER,
                       smIPv6AddressDefaultRoute   InetAddressIPv6
                       }

           smIPv6AddressIndex OBJECT-TYPE
                       SYNTAX  INTEGER
                       ACCESS  read-only
                       STATUS  mandatory
                       DESCRIPTION
                       "The switch module's slot number"
                       ::= { smIPv6AddressEntry 1 }

           smIPv6AddressEntryIndex OBJECT-TYPE
                       SYNTAX  INTEGER
                       ACCESS  read-only
                       STATUS  mandatory
                       DESCRIPTION
                       "The switch module's address entry index"
                       ::= { smIPv6AddressEntry 2 }

           smIPv6AddressType OBJECT-TYPE
                       SYNTAX  INTEGER { static(1), dhcp6(2), link-local(3), autconfig(4), configured-static(5) }
                       ACCESS  read-only
                       STATUS  mandatory
                       DESCRIPTION
                       "The address type."
                       ::= { smIPv6AddressEntry 3 }

           smIPv6Address OBJECT-TYPE
                     SYNTAX  InetAddressIPv6
                     ACCESS  read-only
                     STATUS  mandatory
                     DESCRIPTION
                     "The assigned IPv6 address"
                     ::= { smIPv6AddressEntry 4 }

           smIPv6AddressPrefixLen OBJECT-TYPE
                       SYNTAX  INTEGER (1..128)
                       ACCESS  read-only
                       STATUS  mandatory
                       DESCRIPTION
                       "The prefix length for the given address."
                       ::= { smIPv6AddressEntry 5 }

           smIPv6AddressDefaultRoute OBJECT-TYPE
                     SYNTAX  InetAddressIPv6
                     ACCESS  read-only
                     STATUS  mandatory
                     DESCRIPTION
                     "The default route used for the given address"
                     ::= { smIPv6AddressEntry 6 }

          smIPv6StaticConfigTable OBJECT-TYPE
                      SYNTAX  SEQUENCE OF SmIPv6StaticConfigEntry
                      ACCESS  not-accessible
                      STATUS  mandatory
                      DESCRIPTION
                      "Allows configuration of static IPv6 information for supported
                      IO modules.

                      NOTE: This MIB object is not applicable to modules that are running in
                      Stacking Mode and IP configuration is protected.

                      NOTE: This MIB object is not applicable to modules that
                      do not support IPv6."
                      ::= { switchIPv6Config 3 }

           smIPv6StaticConfigEntry  OBJECT-TYPE
                         SYNTAX SmIPv6StaticConfigEntry
                         ACCESS  not-accessible
                         STATUS  mandatory
                         DESCRIPTION
                         "The static IP address assignment information for an
                         IO module. Once the assignement has taken place the address
                         will show up as a row in the smIPv6AddressTable

                         NOTE: This MIB object is not applicable to modules that are running in
                         Stacking Mode and IP configuration is protected.

                         NOTE: This MIB object is not applicable to modules that
                         do not support IPv6."
                         INDEX { smIPv6StaticIndex}
                         ::= { smIPv6StaticConfigTable 1 }

           SmIPv6StaticConfigEntry ::= SEQUENCE {
                       smIPv6StaticIndex          INTEGER,
                       smIPv6StaticAddress        InetAddressIPv6,
                       smIPv6StaticAddressPrefixLen      INTEGER,
                       smIPv6StaticAddressDefaultRoute   InetAddressIPv6
                       }

           smIPv6StaticIndex OBJECT-TYPE
                     SYNTAX  INTEGER
                     ACCESS  read-only
                     STATUS  mandatory
                     DESCRIPTION
                     "The switch module's slot number"
                     ::= { smIPv6StaticConfigEntry 1 }

           smIPv6StaticAddress OBJECT-TYPE
                     SYNTAX  InetAddressIPv6
                     ACCESS  read-write
                     STATUS  mandatory
                     DESCRIPTION
                     "The assigned IPv6 address.

                     NOTE: If changing with smIPv6StaticAddressPrefixLen and/or
                     smIPv6StaticAddressDefaultRoute sending the update as a
                     single SET command(in one PDU) will minimize the potential
                     downtime of the target switch.

                     NOTE: Sets on this object can take a few seconds. You may
                     need to update your SNMP timeout when modifying this setting."
                     ::= { smIPv6StaticConfigEntry 2 }

           smIPv6StaticAddressPrefixLen OBJECT-TYPE
                     SYNTAX  INTEGER (1..128)
                     ACCESS  read-write
                     STATUS  mandatory
                     DESCRIPTION
                     "The prefix length for the given address.

                     NOTE: If changing with smIPv6StaticAddress and/or
                     smIPv6StaticAddressDefaultRoute sending the update as a
                     single SET command(in one PDU) will minimize the potential
                     downtime of the target switch.

                     NOTE: Sets on this object can take a few seconds. You may
                     need to update your SNMP timeout when modifying this setting."
                     ::= { smIPv6StaticConfigEntry 3 }

           smIPv6StaticAddressDefaultRoute OBJECT-TYPE
                     SYNTAX  InetAddressIPv6
                     ACCESS  read-write
                     STATUS  mandatory
                     DESCRIPTION
                     "The default route used for the given address

                     NOTE: If changing with smIPv6StaticAddressPrefixLen and/or
                     smIPv6StaticAddress sending the update as a
                     single SET command(in one PDU) will minimize the potential
                     downtime of the target switch.

                     NOTE: Sets on this object can take a few seconds. You may
                     need to update your SNMP timeout when modifying this setting."
                     ::= { smIPv6StaticConfigEntry 4 }

         -- ********************************************************************************
         -- Switch module port tables
         -- ********************************************************************************
         switchPortCfg OBJECT IDENTIFIER ::= { switchModuleConfig 2 }

         switchModOnePortCfg  OBJECT IDENTIFIER ::= { switchPortCfg 1 }

          smOnePortCfgTable OBJECT-TYPE
                      SYNTAX  SEQUENCE OF SmOnePortCfgEntry
                      ACCESS  not-accessible
                      STATUS  mandatory
                      DESCRIPTION
                      "Switch Module 1 port configuration information.
                      NOTE: This option is not supported on all I/O modules."
                      ::= { switchModOnePortCfg 1 }

           smOnePortCfgEntry  OBJECT-TYPE
                         SYNTAX SmOnePortCfgEntry
                         ACCESS  not-accessible
                         STATUS  mandatory
                         DESCRIPTION
                         "Switch Module 1 port configuration information table entry"
                         INDEX { smOnePortCfgIndex }
                         ::= { smOnePortCfgTable 1 }

           SmOnePortCfgEntry ::= SEQUENCE {
                       smOnePortCfgIndex INTEGER,
                       smOnePortCfgLabel OCTET STRING,
                       smOnePortCfgType INTEGER,
                       smOnePortCfgLinkSetting INTEGER,
                       smOnePortCfgLinkState INTEGER,
                       smOnePortCfgSpeedSetting OCTET STRING,
                       smOnePortCfgSpeedStatus OCTET STRING,
                       smOnePortCfgAvailSpeeds OCTET STRING,
                       smOnePortCfgMedia INTEGER,
                       smOnePortCfgProtocol INTEGER,
                       smOnePortCfgWidth INTEGER,
                       smOnePortCfgCableLength INTEGER,
                       smOnePortCfgCableType OCTET STRING,
                       smOnePortCfgVendorName OCTET STRING,
                       smOnePortCfgCompatibility INTEGER,
                       smOnePortCfgDataRate INTEGER
                       }

           smOnePortCfgIndex OBJECT-TYPE
                       SYNTAX  INTEGER
                       ACCESS  read-only
                       STATUS  mandatory
                       DESCRIPTION
                       "Switch Module 1 port sequence index."
                       ::= { smOnePortCfgEntry 1 }

           smOnePortCfgLabel OBJECT-TYPE
                        SYNTAX  OCTET STRING
                        ACCESS  read-only
                        STATUS  mandatory
                        DESCRIPTION
                        "Switch Module 1 port label"
                        ::= { smOnePortCfgEntry 2 }

           smOnePortCfgType OBJECT-TYPE
                        SYNTAX  INTEGER {
                          unused(0),
                          externalPort(1),
                          externalManagementPort(2),
                          externalDualPort(3),
                          bladePort(4),
                          mmManagementPort(5),
                          uplinkPort(6),
                          interModulePort(7),
                          interModuleManagementPort(8),
                          interModuleDualPort(9),
                          interModuleExternalBridgePort(10),
                          interModuleDualInternalBridgePort(11)
                        }
                        ACCESS  read-only
                        STATUS  mandatory
                        DESCRIPTION
                        "Switch Module 1 port type:
                        External port: This port is connected to external device and is for data traffic.
                        External management port: This port is solely for external management connection.
                                This port is not used for data traffic from remote to blades.
                        External dual port: This external port is used for both data traffic to blades as well as for management.
                        Blade port: This port is connected to the blade.
                        Management Module Management port: This port is connected to the Management Module.
                        Uplink port: This port is configured for up link functionality.
                        Inter-Module port: This port is either by design connected to another I/O Module,
                                by user configured, or by MM setting the port type.
                        Inter-Module Management port: This port is connected to another I/O Module for management purpose.
                                The port type is either by design connected to another I/O Module, by user configured,
                                or by MM setting the port type.
                        Inter-Module Dual port:  The port is connected to another I/O Module and can be used for both data
                                and management purposes. The port type is either by design connected to another I/O Module,
                                by user configured, or by MM setting the port type."
                        ::= { smOnePortCfgEntry 3 }

           smOnePortCfgLinkSetting OBJECT-TYPE
                        SYNTAX  INTEGER {
                          down(0),
                          up(1)
                        }
                        ACCESS  read-write
                        STATUS  mandatory
                        DESCRIPTION
                        "Current port link setting for Switch Module 1."
                        ::= { smOnePortCfgEntry 4 }

           smOnePortCfgLinkState OBJECT-TYPE
                        SYNTAX  INTEGER {
                          down(0),
                          up(1),
                          initialized(2)
                        }
                        ACCESS  read-only
                        STATUS  mandatory
                        DESCRIPTION
                        "Current port link state of Switch Module 1."
                        ::= { smOnePortCfgEntry 5 }

           smOnePortCfgSpeedSetting OBJECT-TYPE
                        SYNTAX  OCTET STRING
                        ACCESS  read-write
                        STATUS  mandatory
                        DESCRIPTION
                        "Set the port speed using the data rate and duplex value. For examples:
                        100mh: 100 Mbps in Half Duplex;
                        10gf: 10 Gbps in Full Duplex;
                        auto: The working speed of the physical port can be tuned automatically.

                        NOTE: Only the speeds from smOnePortCfgAvailSpeeds object are applicable to setting
                        this mib object."
                        ::= { smOnePortCfgEntry 6 }

           smOnePortCfgSpeedStatus OBJECT-TYPE
                        SYNTAX  OCTET STRING
                        ACCESS  read-only
                        STATUS  mandatory
                        DESCRIPTION
                        "Current port speed of Switch Module 1."
                        ::= { smOnePortCfgEntry 7 }

           smOnePortCfgAvailSpeeds OBJECT-TYPE
                        SYNTAX  OCTET STRING
                        ACCESS  read-only
                        STATUS  mandatory
                        DESCRIPTION
                        "Available speed setting per port for Switch Module 1.
                        If there is more than one setting, the speeds are separated by a comma and then a space."
                        ::= { smOnePortCfgEntry 8 }

           smOnePortCfgMedia OBJECT-TYPE
                        SYNTAX  INTEGER {
                          copper(0),
                          serdes(1),
                          opticalShortHaul(32),
                          opticalLongHaul(48),
                          notApplicable(255)
                        }
                        ACCESS  read-only
                        STATUS  mandatory
                        DESCRIPTION
                        "Port media type of Switch Module 1."
                        ::= { smOnePortCfgEntry 9 }

           smOnePortCfgProtocol OBJECT-TYPE
                        SYNTAX  INTEGER {
                          ethernet(16),
                          fibreChannel(32),
                          scalability(48),
                          infiniband(64),
                          pciExpress(80),
                          myrinet(112),
                          notApplicable(255)
                        }
                        ACCESS  read-only
                        STATUS  mandatory
                        DESCRIPTION
                        "Port protocol of Switch Module 1."
                        ::= { smOnePortCfgEntry 10 }

           smOnePortCfgWidth OBJECT-TYPE
                        SYNTAX  INTEGER
                        ACCESS  read-only
                        STATUS  mandatory
                        DESCRIPTION
                        "The width of the port in terms of how many combined cables are present for Switch Module 1.
                         A value of 0 indicates this field is not applicable to the switch ports.
                         This data is also known as the lane count."
                        ::= { smOnePortCfgEntry 11 }

           smOnePortCfgCableLength OBJECT-TYPE
                        SYNTAX  INTEGER
                        ACCESS  read-only
                        STATUS  mandatory
                        DESCRIPTION
                        "The length (in meters) of the cable supported by this port for Switch Module 1.
                         A value of 0 indicates this field is not applicable to the switch ports."
                        ::= { smOnePortCfgEntry 12 }

           smOnePortCfgCableType OBJECT-TYPE
                        SYNTAX  OCTET STRING
                        ACCESS  read-only
                        STATUS  mandatory
                        DESCRIPTION
                        "External cable type for this port, for example, active copper or passive fiber."
                        ::= { smOnePortCfgEntry 13 }

           smOnePortCfgVendorName OBJECT-TYPE
                        SYNTAX  OCTET STRING
                        ACCESS  read-only
                        STATUS  mandatory
                        DESCRIPTION
                        "The cable manufacturer."
                        ::= { smOnePortCfgEntry 14 }

           smOnePortCfgCompatibility OBJECT-TYPE
                        SYNTAX  INTEGER {
                          incompatible(0),
                          compatible(1),
                          compatibleNotRecommended(2),
                          notApplicable(255)
                        }
                        ACCESS  read-only
                        STATUS  mandatory
                        DESCRIPTION
                        "Compatibility of the external cable that is plugged into the port."
                        ::= { smOnePortCfgEntry 15 }

           smOnePortCfgDataRate OBJECT-TYPE
                        SYNTAX  INTEGER {
                          sdr(0),
                          ddr(1),
                          qdr(2),
                          edr(3),
                          notApplicable(255)
                        }
                        ACCESS  read-only
                        STATUS  mandatory
                        DESCRIPTION
                        "Data rate supported for this port."
                        ::= { smOnePortCfgEntry 16 }


         switchModTwoPortCfg  OBJECT IDENTIFIER ::= { switchPortCfg 2 }

          smTwoPortCfgTable OBJECT-TYPE
                      SYNTAX  SEQUENCE OF SmTwoPortCfgEntry
                      ACCESS  not-accessible
                      STATUS  mandatory
                      DESCRIPTION
                      "Switch Module 2 port configuration information.
                      Note:  This option is not supported on all I/O modules."
                      ::= { switchModTwoPortCfg 1 }

           smTwoPortCfgEntry  OBJECT-TYPE
                         SYNTAX SmTwoPortCfgEntry
                         ACCESS  not-accessible
                         STATUS  mandatory
                         DESCRIPTION
                         "Switch Module 2 port configuration information table entry"
                         INDEX { smTwoPortCfgIndex }
                         ::= { smTwoPortCfgTable 1 }

           SmTwoPortCfgEntry ::= SEQUENCE {
                       smTwoPortCfgIndex INTEGER,
                       smTwoPortCfgLabel OCTET STRING,
                       smTwoPortCfgType INTEGER,
                       smTwoPortCfgLinkSetting INTEGER,
                       smTwoPortCfgLinkState INTEGER,
                       smTwoPortCfgSpeedSetting OCTET STRING,
                       smTwoPortCfgSpeedStatus OCTET STRING,
                       smTwoPortCfgAvailSpeeds OCTET STRING,
                       smTwoPortCfgMedia INTEGER,
                       smTwoPortCfgProtocol INTEGER,
                       smTwoPortCfgWidth INTEGER,
                       smTwoPortCfgCableLength INTEGER,
                       smTwoPortCfgCableType OCTET STRING,
                       smTwoPortCfgVendorName OCTET STRING,
                       smTwoPortCfgCompatibility INTEGER,
                       smTwoPortCfgDataRate INTEGER
                       }

           smTwoPortCfgIndex OBJECT-TYPE
                       SYNTAX  INTEGER
                       ACCESS  read-only
                       STATUS  mandatory
                       DESCRIPTION
                       "Switch Module 2 port sequence index."
                       ::= { smTwoPortCfgEntry 1 }

           smTwoPortCfgLabel OBJECT-TYPE
                        SYNTAX  OCTET STRING
                        ACCESS  read-only
                        STATUS  mandatory
                        DESCRIPTION
                        "Switch Module 2 port label"
                        ::= { smTwoPortCfgEntry 2 }

           smTwoPortCfgType OBJECT-TYPE
                        SYNTAX  INTEGER {
                          unused(0),
                          externalPort(1),
                          externalManagementPort(2),
                          externalDualPort(3),
                          bladePort(4),
                          mmManagementPort(5),
                          uplinkPort(6),
                          interModulePort(7),
                          interModuleManagementPort(8),
                          interModuleDualPort(9),
                          interModuleExternalBridgePort(10),
                          interModuleDualInternalBridgePort(11)
                        }
                        ACCESS  read-only
                        STATUS  mandatory
                        DESCRIPTION
                        "Switch Module 2 port type:
                        External port: This port is connected to external device and is for data traffic.
                        External management port: This port is solely for external management connection.
                                This port is not used for data traffic from remote to blades.
                        External dual port: This external port is used for both data traffic to blades as well as for management.
                        Blade port: This port is connected to the blade.
                        Management Module Management port: This port is connected to the Management Module.
                        Uplink port: This port is configured for up link functionality.
                        Inter-Module port: This port is either by design connected to another I/O Module,
                                by user configured, or by MM setting the port type.
                        Inter-Module Management port: This port is connected to another I/O Module for management purpose.
                                The port type is either by design connected to another I/O Module, by user configured,
                                or by MM setting the port type.
                        Inter-Module Dual port:  The port is connected to another I/O Module and can be used for both data
                                and management purposes. The port type is either by design connected to another I/O Module,
                                by user configured, or by MM setting the port type."
                        ::= { smTwoPortCfgEntry 3 }

           smTwoPortCfgLinkSetting OBJECT-TYPE
                        SYNTAX  INTEGER {
                          down(0),
                          up(1)
                        }
                        ACCESS  read-write
                        STATUS  mandatory
                        DESCRIPTION
                        "Current port link setting for Switch Module 2."
                        ::= { smTwoPortCfgEntry 4 }

           smTwoPortCfgLinkState OBJECT-TYPE
                        SYNTAX  INTEGER {
                          down(0),
                          up(1),
                          initialized(2)
                        }
                        ACCESS  read-only
                        STATUS  mandatory

                        DESCRIPTION
                        "Current port link state of Switch Module 2."
                        ::= { smTwoPortCfgEntry 5 }

           smTwoPortCfgSpeedSetting OBJECT-TYPE
                        SYNTAX  OCTET STRING
                        ACCESS  read-write
                        STATUS  mandatory
                        DESCRIPTION
                        "Set the port speed using the data rate and duplex value. For examples:
                        100mf: 100Mbps in Half Duplex;
                        10gf: 10 Gbps in Full Duplex;
                        auto: The working speed of the physical port can be tuned automatically.

                        NOTE: Only the speeds from smTwoPortCfgAvailSpeeds are applicable to setting
                        this mib object."
                        ::= { smTwoPortCfgEntry 6 }

           smTwoPortCfgSpeedStatus OBJECT-TYPE
                        SYNTAX  OCTET STRING
                        ACCESS  read-only
                        STATUS  mandatory
                        DESCRIPTION
                        "Current port speed of Switch Module 2."
                        ::= { smTwoPortCfgEntry 7 }

           smTwoPortCfgAvailSpeeds OBJECT-TYPE
                        SYNTAX  OCTET STRING
                        ACCESS  read-only
                        STATUS  mandatory
                        DESCRIPTION
                        "Available speed setting per port for Switch Module 2.
                        If there is more than one setting, the speeds are separated by a comma and then a space."
                        ::= { smTwoPortCfgEntry 8 }

           smTwoPortCfgMedia OBJECT-TYPE
                        SYNTAX  INTEGER {
                          copper(0),
                          serdes(1),
                          opticalShortHaul(32),
                          opticalLongHaul(48),
                          notApplicable(255)
                        }
                        ACCESS  read-only
                        STATUS  mandatory
                        DESCRIPTION
                        "Port media type of Switch Module 2."
                        ::= { smTwoPortCfgEntry 9 }

           smTwoPortCfgProtocol OBJECT-TYPE
                        SYNTAX  INTEGER {
                          ethernet(16),
                          fibreChannel(32),
                          scalability(48),
                          infiniband(64),
                          pciExpress(80),
                          myrinet(112),
                          notApplicable(255)
                        }
                        ACCESS  read-only
                        STATUS  mandatory
                        DESCRIPTION
                        "Port protocol of Switch Module 2."
                        ::= { smTwoPortCfgEntry 10 }

           smTwoPortCfgWidth OBJECT-TYPE
                        SYNTAX  INTEGER
                        ACCESS  read-only
                        STATUS  mandatory
                        DESCRIPTION
                        "The width of the port in terms of how many combined cables are present for Switch Module 2.
                         A value of 0 indicates this field is not applicable to the switch ports.
                         This data is also known as the lane count."
                        ::= { smTwoPortCfgEntry 11 }

           smTwoPortCfgCableLength OBJECT-TYPE
                        SYNTAX  INTEGER
                        ACCESS  read-only
                        STATUS  mandatory
                        DESCRIPTION
                        "The length (in meters) of the cable supported by this port for Switch Module 2.
                         A value of 0 indicates this field is not applicable to the switch ports."
                        ::= { smTwoPortCfgEntry 12 }

           smTwoPortCfgCableType OBJECT-TYPE
                        SYNTAX  OCTET STRING
                        ACCESS  read-only
                        STATUS  mandatory
                        DESCRIPTION
                        "External cable type for this port, for example, active copper or passive fiber."
                        ::= { smTwoPortCfgEntry 13 }

           smTwoPortCfgVendorName OBJECT-TYPE
                        SYNTAX  OCTET STRING
                        ACCESS  read-only
                        STATUS  mandatory
                        DESCRIPTION
                        "The cable manufacturer."
                        ::= { smTwoPortCfgEntry 14 }

           smTwoPortCfgCompatibility OBJECT-TYPE
                        SYNTAX  INTEGER {
                          incompatible(0),
                          compatible(1),
                          compatibleNotRecommended(2),
                          notApplicable(255)
                        }
                        ACCESS  read-only
                        STATUS  mandatory
                        DESCRIPTION
                        "Compatibility of the external cable that is plugged into the port."
                        ::= { smTwoPortCfgEntry 15 }

           smTwoPortCfgDataRate OBJECT-TYPE
                        SYNTAX  INTEGER {
                          sdr(0),
                          ddr(1),
                          qdr(2),
                          edr(3),
                          notApplicable(255)
                        }
                        ACCESS  read-only
                        STATUS  mandatory
                        DESCRIPTION
                        "Data rate supported for this port."
                        ::= { smTwoPortCfgEntry 16 }

         switchModThreePortCfg  OBJECT IDENTIFIER ::= { switchPortCfg 3 }

          smThreePortCfgTable OBJECT-TYPE
                      SYNTAX  SEQUENCE OF SmThreePortCfgEntry
                      ACCESS  not-accessible
                      STATUS  mandatory
                      DESCRIPTION
                      "Switch Module 3 port configuration information.
                      Note:  This option is not supported on all I/O modules."
                      ::= { switchModThreePortCfg 1 }

           smThreePortCfgEntry  OBJECT-TYPE
                         SYNTAX SmThreePortCfgEntry
                         ACCESS  not-accessible
                         STATUS  mandatory
                         DESCRIPTION
                         "Switch Module 3 port configuration information table entry"
                         INDEX { smThreePortCfgIndex }
                         ::= { smThreePortCfgTable 1 }

           SmThreePortCfgEntry ::= SEQUENCE {
                       smThreePortCfgIndex INTEGER,
                       smThreePortCfgLabel OCTET STRING,
                       smThreePortCfgType INTEGER,
                       smThreePortCfgLinkSetting INTEGER,
                       smThreePortCfgLinkState INTEGER,
                       smThreePortCfgSpeedSetting OCTET STRING,
                       smThreePortCfgSpeedStatus OCTET STRING,
                       smThreePortCfgAvailSpeeds OCTET STRING,
                       smThreePortCfgMedia INTEGER,
                       smThreePortCfgProtocol INTEGER,
                       smThreePortCfgWidth INTEGER,
                       smThreePortCfgCableLength INTEGER,
                       smThreePortCfgCableType OCTET STRING,
                       smThreePortCfgVendorName OCTET STRING,
                       smThreePortCfgCompatibility INTEGER,
                       smThreePortCfgDataRate INTEGER
                       }

           smThreePortCfgIndex OBJECT-TYPE
                       SYNTAX  INTEGER
                       ACCESS  read-only
                       STATUS  mandatory
                       DESCRIPTION
                       "Switch Module 3 port sequence index."
                       ::= { smThreePortCfgEntry 1 }

           smThreePortCfgLabel OBJECT-TYPE
                        SYNTAX  OCTET STRING
                        ACCESS  read-only
                        STATUS  mandatory
                        DESCRIPTION
                        "Switch Module 3 port label"
                        ::= { smThreePortCfgEntry 2 }

           smThreePortCfgType OBJECT-TYPE
                        SYNTAX  INTEGER {
                          unused(0),
                          externalPort(1),
                          externalManagementPort(2),
                          externalDualPort(3),
                          bladePort(4),
                          mmManagementPort(5),
                          uplinkPort(6),
                          interModulePort(7),
                          interModuleManagementPort(8),
                          interModuleDualPort(9),
                          interModuleExternalBridgePort(10),
                          interModuleDualInternalBridgePort(11)
                        }
                        ACCESS  read-only
                        STATUS  mandatory
                        DESCRIPTION
                        "Switch Module 3 port type:
                        External port: This port is connected to external device and is for data traffic.
                        External management port: This port is solely for external management connection.
                                This port is not used for data traffic from remote to blades.
                        External dual port: This external port is used for both data traffic to blades as well as for management.
                        Blade port: This port is connected to the blade.
                        Management Module Management port: This port is connected to the Management Module.
                        Uplink port: This port is configured for up link functionality.
                        Inter-Module port: This port is either by design connected to another I/O Module,
                                by user configured, or by MM setting the port type.
                        Inter-Module Management port: This port is connected to another I/O Module for management purpose.
                                The port type is either by design connected to another I/O Module, by user configured,
                                or by MM setting the port type.
                        Inter-Module Dual port:  The port is connected to another I/O Module and can be used for both data
                                and management purposes. The port type is either by design connected to another I/O Module,
                                by user configured, or by MM setting the port type."
                        ::= { smThreePortCfgEntry 3 }

           smThreePortCfgLinkSetting OBJECT-TYPE
                        SYNTAX  INTEGER {
                          down(0),
                          up(1)
                        }
                        ACCESS  read-write
                        STATUS  mandatory
                        DESCRIPTION
                        "Current port link setting for Switch Module 3."
                        ::= { smThreePortCfgEntry 4 }

           smThreePortCfgLinkState OBJECT-TYPE
                        SYNTAX  INTEGER {
                          down(0),
                          up(1),
                          initialized(2)
                        }
                        ACCESS  read-only
                        STATUS  mandatory
                        DESCRIPTION
                        "Current port link state of Switch Module 3."
                        ::= { smThreePortCfgEntry 5 }

           smThreePortCfgSpeedSetting OBJECT-TYPE
                        SYNTAX  OCTET STRING
                        ACCESS  read-write
                        STATUS  mandatory
                        DESCRIPTION
                        "Set the port speed using the data rate and duplex value. For examples:
                        100mf: 100Mbps in Half Duplex;
                        10gf: 10 Gbps in Full Duplex;
                        auto: The working speed of the physical port can be tuned automatically.

                        NOTE: Only the speeds from smThreePortCfgAvailSpeeds are applicable to setting
                        this mib object."
                        ::= { smThreePortCfgEntry 6 }

           smThreePortCfgSpeedStatus OBJECT-TYPE
                        SYNTAX  OCTET STRING
                        ACCESS  read-only
                        STATUS  mandatory
                        DESCRIPTION
                        "Current port speed of Switch Module 3."
                        ::= { smThreePortCfgEntry 7 }

           smThreePortCfgAvailSpeeds OBJECT-TYPE
                        SYNTAX  OCTET STRING
                        ACCESS  read-only
                        STATUS  mandatory
                        DESCRIPTION
                        "Available speed setting per port for Switch Module 3.
                        If there is more than one setting, the speeds are separated by a comma and then a space."
                        ::= { smThreePortCfgEntry 8 }

           smThreePortCfgMedia OBJECT-TYPE
                        SYNTAX  INTEGER {
                          copper(0),
                          serdes(1),
                          opticalShortHaul(32),
                          opticalLongHaul(48),
                          notApplicable(255)
                        }
                        ACCESS  read-only
                        STATUS  mandatory
                        DESCRIPTION
                        "Port media type of Switch Module 3."
                        ::= { smThreePortCfgEntry 9 }

           smThreePortCfgProtocol OBJECT-TYPE
                        SYNTAX  INTEGER {
                          ethernet(16),
                          fibreChannel(32),
                          scalability(48),
                          infiniband(64),
                          pciExpress(80),
                          myrinet(112),
                          notApplicable(255)
                        }
                        ACCESS  read-only
                        STATUS  mandatory
                        DESCRIPTION
                        "Port protocol of Switch Module 3."
                        ::= { smThreePortCfgEntry 10 }

           smThreePortCfgWidth OBJECT-TYPE
                        SYNTAX  INTEGER
                        ACCESS  read-only
                        STATUS  mandatory
                        DESCRIPTION
                        "The width of the port in terms of how many combined cables are present for Switch Module 3.
                         A value of 0 indicates this field is not applicable to the switch ports.
                         This data is also known as the lane count."
                        ::= { smThreePortCfgEntry 11 }

           smThreePortCfgCableLength OBJECT-TYPE
                        SYNTAX  INTEGER
                        ACCESS  read-only
                        STATUS  mandatory
                        DESCRIPTION
                        "The length (in meters) of the cable supported by this port for Switch Module 3.
                         A value of 0 indicates this field is not applicable to the switch ports."
                        ::= { smThreePortCfgEntry 12 }

           smThreePortCfgCableType OBJECT-TYPE
                        SYNTAX  OCTET STRING
                        ACCESS  read-only
                        STATUS  mandatory
                        DESCRIPTION
                        "External cable type for this port, for example, active copper or passive fiber."
                        ::= { smThreePortCfgEntry 13 }

           smThreePortCfgVendorName OBJECT-TYPE
                        SYNTAX  OCTET STRING
                        ACCESS  read-only
                        STATUS  mandatory
                        DESCRIPTION
                        "The cable manufacturer."
                        ::= { smThreePortCfgEntry 14 }

           smThreePortCfgCompatibility OBJECT-TYPE
                        SYNTAX  INTEGER {
                          incompatible(0),
                          compatible(1),
                          compatibleNotRecommended(2),
                          notApplicable(255)
                        }
                        ACCESS  read-only
                        STATUS  mandatory
                        DESCRIPTION
                        "Compatibility of the external cable that is plugged into the port."
                        ::= { smThreePortCfgEntry 15 }

           smThreePortCfgDataRate OBJECT-TYPE
                        SYNTAX  INTEGER {
                          sdr(0),
                          ddr(1),
                          qdr(2),
                          edr(3),
                          notApplicable(255)
                        }
                        ACCESS  read-only
                        STATUS  mandatory
                        DESCRIPTION
                        "Data rate supported for this port."
                        ::= { smThreePortCfgEntry 16 }


         switchModFourPortCfg  OBJECT IDENTIFIER ::= { switchPortCfg 4 }

          smFourPortCfgTable OBJECT-TYPE
                      SYNTAX  SEQUENCE OF SmFourPortCfgEntry
                      ACCESS  not-accessible
                      STATUS  mandatory
                      DESCRIPTION
                      "Switch Module 4 port configuration information.
                      Note:  This option is not supported on all I/O modules."
                      ::= { switchModFourPortCfg 1 }

           smFourPortCfgEntry  OBJECT-TYPE
                         SYNTAX SmFourPortCfgEntry
                         ACCESS  not-accessible
                         STATUS  mandatory
                         DESCRIPTION
                         "Switch Module 4 port configuration information table entry"
                         INDEX { smFourPortCfgIndex }
                         ::= { smFourPortCfgTable 1 }

           SmFourPortCfgEntry ::= SEQUENCE {
                       smFourPortCfgIndex INTEGER,
                       smFourPortCfgLabel OCTET STRING,
                       smFourPortCfgType INTEGER,
                       smFourPortCfgLinkSetting INTEGER,
                       smFourPortCfgLinkState INTEGER,
                       smFourPortCfgSpeedSetting OCTET STRING,
                       smFourPortCfgSpeedStatus OCTET STRING,
                       smFourPortCfgAvailSpeeds OCTET STRING,
                       smFourPortCfgMedia INTEGER,
                       smFourPortCfgProtocol INTEGER,
                       smFourPortCfgWidth INTEGER,
                       smFourPortCfgCableLength INTEGER,
                       smFourPortCfgCableType OCTET STRING,
                       smFourPortCfgVendorName OCTET STRING,
                       smFourPortCfgCompatibility INTEGER,
                       smFourPortCfgDataRate INTEGER
                       }

           smFourPortCfgIndex OBJECT-TYPE
                       SYNTAX  INTEGER
                       ACCESS  read-only
                       STATUS  mandatory
                       DESCRIPTION
                       "Switch Module 4 port sequence index."
                       ::= { smFourPortCfgEntry 1 }

           smFourPortCfgLabel OBJECT-TYPE
                        SYNTAX  OCTET STRING
                        ACCESS  read-only
                        STATUS  mandatory
                        DESCRIPTION
                        "Switch Module 4 port label"
                        ::= { smFourPortCfgEntry 2 }

           smFourPortCfgType OBJECT-TYPE
                        SYNTAX  INTEGER {
                          unused(0),
                          externalPort(1),
                          externalManagementPort(2),
                          externalDualPort(3),
                          bladePort(4),
                          mmManagementPort(5),
                          uplinkPort(6),
                          interModulePort(7),
                          interModuleManagementPort(8),
                          interModuleDualPort(9),
                          interModuleExternalBridgePort(10),
                          interModuleDualInternalBridgePort(11)
                        }
                        ACCESS  read-only
                        STATUS  mandatory
                        DESCRIPTION
                        "Switch Module 4 port type:
                        External port: This port is connected to external device and is for data traffic.
                        External management port: This port is solely for external management connection.
                                This port is not used for data traffic from remote to blades.
                        External dual port: This external port is used for both data traffic to blades as well as for management.
                        Blade port: This port is connected to the blade.
                        Management Module Management port: This port is connected to the Management Module.
                        Uplink port: This port is configured for up link functionality.
                        Inter-Module port: This port is either by design connected to another I/O Module,
                                by user configured, or by MM setting the port type.
                        Inter-Module Management port: This port is connected to another I/O Module for management purpose.
                                The port type is either by design connected to another I/O Module, by user configured,
                                or by MM setting the port type.
                        Inter-Module Dual port:  The port is connected to another I/O Module and can be used for both data
                                and management purposes. The port type is either by design connected to another I/O Module,
                                by user configured, or by MM setting the port type."
                        ::= { smFourPortCfgEntry 3 }

           smFourPortCfgLinkSetting OBJECT-TYPE
                        SYNTAX  INTEGER {
                          down(0),
                          up(1)
                        }
                        ACCESS  read-write
                        STATUS  mandatory
                        DESCRIPTION
                        "Current port link setting for Switch Module 4."
                        ::= { smFourPortCfgEntry 4 }

           smFourPortCfgLinkState OBJECT-TYPE
                        SYNTAX  INTEGER {
                          down(0),
                          up(1),
                          initialized(2)
                        }
                        ACCESS  read-only
                        STATUS  mandatory
                        DESCRIPTION
                        "Current port link state of Switch Module 4."
                        ::= { smFourPortCfgEntry 5 }

           smFourPortCfgSpeedSetting OBJECT-TYPE
                        SYNTAX  OCTET STRING
                        ACCESS  read-write
                        STATUS  mandatory
                        DESCRIPTION
                        "Set the port speed using the data rate and duplex value. For examples:
                        100mf: 100Mbps in Half Duplex;
                        10gf: 10 Gbps in Full Duplex;
                        auto: The working speed of the physical port can be tuned automatically.

                        NOTE: Only the speeds from smFourPortCfgAvailSpeeds are applicable to setting
                        this mib object."
                        ::= { smFourPortCfgEntry 6 }

           smFourPortCfgSpeedStatus OBJECT-TYPE
                        SYNTAX  OCTET STRING
                        ACCESS  read-only
                        STATUS  mandatory
                        DESCRIPTION
                        "Current port speed of Switch Module 4."
                        ::= { smFourPortCfgEntry 7 }


           smFourPortCfgAvailSpeeds OBJECT-TYPE
                        SYNTAX  OCTET STRING
                        ACCESS  read-only
                        STATUS  mandatory
                        DESCRIPTION
                        "Available speed setting per port for Switch Module 4.
                        If there is more than one setting, the speeds are separated by a comma and then a space."
                        ::= { smFourPortCfgEntry 8 }

           smFourPortCfgMedia OBJECT-TYPE
                        SYNTAX  INTEGER {
                          copper(0),
                          serdes(1),
                          opticalShortHaul(32),
                          opticalLongHaul(48),
                          notApplicable(255)
                        }
                        ACCESS  read-only
                        STATUS  mandatory
                        DESCRIPTION
                        "Port media type of Switch Module 4."
                        ::= { smFourPortCfgEntry 9 }

           smFourPortCfgProtocol OBJECT-TYPE
                        SYNTAX  INTEGER {
                          ethernet(16),
                          fibreChannel(32),
                          scalability(48),
                          infiniband(64),
                          pciExpress(80),
                          myrinet(112),
                          notApplicable(255)
                        }
                        ACCESS  read-only
                        STATUS  mandatory
                        DESCRIPTION
                        "Port protocol of Switch Module 4."
                        ::= { smFourPortCfgEntry 10 }

           smFourPortCfgWidth OBJECT-TYPE
                        SYNTAX  INTEGER
                        ACCESS  read-only
                        STATUS  mandatory
                        DESCRIPTION
                        "The width of the port in terms of how many combined cables are present for Switch Module 4.
                         A value of 0 indicates this field is not applicable to the switch ports.
                         This data is also known as the lane count."
                        ::= { smFourPortCfgEntry 11 }

           smFourPortCfgCableLength OBJECT-TYPE
                        SYNTAX  INTEGER
                        ACCESS  read-only
                        STATUS  mandatory
                        DESCRIPTION
                        "The length (in meters) of the cable supported by this port for Switch Module 4.
                         A value of 0 indicates this field is not applicable to the switch ports."
                        ::= { smFourPortCfgEntry 12 }

           smFourPortCfgCableType OBJECT-TYPE
                        SYNTAX  OCTET STRING
                        ACCESS  read-only
                        STATUS  mandatory
                        DESCRIPTION
                        "External cable type for this port, for example, active copper or passive fiber."
                        ::= { smFourPortCfgEntry 13 }

           smFourPortCfgVendorName OBJECT-TYPE
                        SYNTAX  OCTET STRING
                        ACCESS  read-only
                        STATUS  mandatory
                        DESCRIPTION
                        "The cable manufacturer."
                        ::= { smFourPortCfgEntry 14 }

           smFourPortCfgCompatibility OBJECT-TYPE
                        SYNTAX  INTEGER {
                          incompatible(0),
                          compatible(1),
                          compatibleNotRecommended(2),
                          notApplicable(255)
                        }
                        ACCESS  read-only
                        STATUS  mandatory
                        DESCRIPTION
                        "Compatibility of the external cable that is plugged into the port."
                        ::= { smFourPortCfgEntry 15 }

           smFourPortCfgDataRate OBJECT-TYPE
                        SYNTAX  INTEGER {
                          sdr(0),
                          ddr(1),
                          qdr(2),
                          edr(3),
                          notApplicable(255)
                        }
                        ACCESS  read-only
                        STATUS  mandatory
                        DESCRIPTION
                        "Data rate supported for this port."
                        ::= { smFourPortCfgEntry 16 }

    chassisTopology OBJECT IDENTIFIER ::= { components 4 }

     chassisResponseVersion  OBJECT-TYPE
                 SYNTAX  INTEGER
                 ACCESS  read-only
                 STATUS  mandatory
                 DESCRIPTION
                 "Chassis response version."
                 ::= { chassisTopology 1 }

     chassisFlags OBJECT-TYPE
                 SYNTAX  INTEGER {
                   rackOrStandAlone(0),
                   serverBlade(1)
                 }
                 ACCESS  read-only
                 STATUS  mandatory
                 DESCRIPTION
                 "Chassis flags.
                 1 = a server blade chassis, 0 = a rack or standalone chassis."
                 ::= { chassisTopology 2 }

     chassisNoOfFPsSupported OBJECT-TYPE
                 SYNTAX  INTEGER
                 ACCESS  read-only
                 STATUS  deprecated
                 DESCRIPTION
                 "This object is deprecated because the power modules'
                 fan packs are integrated into the power modules and are not
                 removable as on previous power modules.

                 Number of fan packs (FPs) supported.

                 NOTE: Fan packs are also referred to as Power Module Cooling Devices."
                 ::= { chassisTopology 18 }

     chassisNoOfBayDevicesSupported OBJECT-TYPE
                 SYNTAX  INTEGER
                 ACCESS  read-only
                 STATUS  mandatory
                 DESCRIPTION
                 "Maximum number of bays found in the chassis."
                 ::= { chassisTopology 19 }

     chassisNoOfSMsSupported OBJECT-TYPE
                 SYNTAX  INTEGER
                 ACCESS  read-only
                 STATUS  mandatory
                 DESCRIPTION
                 "Number of switch modules (SMs) supported."
                 ::= { chassisTopology 20 }

     chassisNoOfMMsSupported OBJECT-TYPE
                 SYNTAX  INTEGER
                 ACCESS  read-only
                 STATUS  mandatory
                 DESCRIPTION
                 "Number of management modules (MMs) supported."
                 ::= { chassisTopology 21 }

     chassisNoOfPMsSupported OBJECT-TYPE
                 SYNTAX  INTEGER
                 ACCESS  read-only
                 STATUS  mandatory
                 DESCRIPTION
                 "Number of power modules (PMs) supported."
                 ::= { chassisTopology 22 }

     chassisNoOfRearLEDCardsSupported OBJECT-TYPE
                 SYNTAX  INTEGER
                 ACCESS  read-only
                 STATUS  mandatory
                 DESCRIPTION
                 "Number of rear LED cards supported."
                 ::= { chassisTopology 23 }

     chassisNoOfChassisFansSupported OBJECT-TYPE
                 SYNTAX  INTEGER
                 ACCESS  read-only
                 STATUS  mandatory
                 DESCRIPTION
                 "Number of chassis fans supported."
                 ::= { chassisTopology 24 }

     chassisBayDevicesInstalled OBJECT-TYPE
                 SYNTAX  OCTET STRING
                 ACCESS  read-only
                 STATUS  mandatory
                 DESCRIPTION
                 "The bay devices that are installed in the chassis.
                 The bay devices are listed as a bitmap.  The bitmap is a
                 string containing a list of 1's and 0's that is as long as
                 the number of bay devices supported. For devices that fill
                 multiple bays, the bit mask will indicate the
                 primary/lowest bay as occupied. If a device is installed in a
                 bay, a 1 is present in the string in the position representing
                 the bay ID as read from left to right.  For example, if devices
                 are installed in bays 1, 5, and 13, and 14 bays are supported,
                 the string would look like '10001000000010'."
                 ::= { chassisTopology 25 }

     chassisSMsInstalled OBJECT-TYPE
                 SYNTAX  OCTET STRING
                 ACCESS  read-only
                 STATUS  mandatory
                 DESCRIPTION
                 "The switch modules that are installed on the chassis.
                 The switch modules are listed as a bitmap.  The bitmap is a
                 string containing a list of 1's and 0's that is as long as
                 the number of switch modules supported.  If a switch module is
                 installed in a bay, a 1 is present in the string in the position
                 representing the bay ID as read from left to right.  For example,
                 if switch modules are installed in bays 1 and 3, and 4 switch modules
                 are supported, the string would look like '1011'."
                 ::= { chassisTopology 29 }

     chassisMMsInstalled OBJECT-TYPE
                 SYNTAX  OCTET STRING
                 ACCESS  read-only
                 STATUS  mandatory
                 DESCRIPTION
                 "The management modules that are installed on the chassis.
                 The management modules are listed as a bitmap.  The bitmap is a
                 string containing a list of 1's and 0's that is as long as the
                 number of management modules supported.  If a management module is installed
                 in a bay, a 1 is present in the string in the position representing
                 the bay ID as read from left to right.  For example, if a management module
                 is installed in bay 1, and 2 management modules are supported, the
                 string would look like '10'."
                 ::= { chassisTopology 30 }

     chassisPMsInstalled OBJECT-TYPE
                 SYNTAX  OCTET STRING
                 ACCESS  read-only
                 STATUS  mandatory
                 DESCRIPTION
                 "The power modules that are installed on the chassis.
                 The power modules are listed as a bitmap.  The bitmap is a
                 string containing a list of 1's and 0's that is as long as
                 the number of power modules supported.  If a power module is
                 installed in a bay, a 1 is present in the string in the position
                 representing the bay ID as read from left to right.  For example,
                 if power modules are installed in bays 1 and 3, and 4 power modules
                 are supported, the string would look like '1010'."
                 ::= { chassisTopology 31 }

     chassisRearLEDCardInstalled OBJECT-TYPE
                 SYNTAX  INTEGER {
                   no(0),
                   yes(1)
                 }
                 ACCESS  read-only
                 STATUS  mandatory
                 DESCRIPTION
                 "Indicates whether at least one rear LED card is installed."
                 ::= { chassisTopology 32 }

     chassisFansInstalled OBJECT-TYPE
                 SYNTAX  OCTET STRING
                 ACCESS  read-only
                 STATUS  mandatory
                 DESCRIPTION
                 "The chassis fans that are installed on the chassis.
                 They are listed as a bitmap.  The bitmap is a
                 string containing a list of 1's and 0's that is as long as
                 the number of supported.  If it is installed in a
                 bay, a 1 is present in the string in the position representing
                 the bay ID as read from left to right.  For example, if it
                 is installed in bay 1, and 2 are supported, the string
                 would look like '10'."
                 ::= { chassisTopology 33 }

     chassisActiveMM OBJECT-TYPE
                 SYNTAX  INTEGER
                 ACCESS  read-only
                 STATUS  mandatory
                 DESCRIPTION
                 "The active management module (MM)."
                 ::= { chassisTopology 34 }

     chassisFPsInstalled OBJECT-TYPE
                 SYNTAX  OCTET STRING
                 ACCESS  read-only
                 STATUS  deprecated
                 DESCRIPTION
                 "This object is deprecated because the power modules'
                 fan packs are integrated into the power modules and are not
                 removable as on previous power modules.

                 The fan packs that are installed on the chassis.
                 The fan packs are listed as a bitmap.  The bitmap is a
                 string containing a list of 1's and 0's that is as long as
                 the number of fan packs supported.  If a fan pack is
                 installed in a bay, a 1 is present in the string in the position
                 representing the bay ID as read from left to right.  For example,
                 if fan packs are installed in bays 1 and 3, and 4 fan packs
                 are supported, the string would look like '1010'.

                 NOTE: Fan packs are also referred to as Power Module Cooling Devices."
                 ::= { chassisTopology 37 }

     chassisType OBJECT-TYPE
                 SYNTAX  INTEGER {
                        flex(101)
                 }
                 ACCESS  read-only
                 STATUS  mandatory
                 DESCRIPTION
                 "The type of the chassis.  
                 This MIB object should be used in conjunction
                 with chassisSubType MIB object to determine the characteristic of the chassis."
                 ::= { chassisTopology 38 }

     chassisSubtype OBJECT-TYPE
                 SYNTAX  INTEGER {
                        tracewell4(48),
                        tracewell8(49),
                        tracewell7(50),
                        flex(101),
                        unknown(255)
                 }
                 ACCESS  read-only
                 STATUS  mandatory
                 DESCRIPTION
                 "The subtype of the chassis.  This MIB object should be used in conjunction with
                 chassisType MIB object to determine the characteristic of the chassis."
                 ::= { chassisTopology 39 }

     chassisNoOfRearLEDCardsInstalled OBJECT-TYPE
                 SYNTAX  OCTET STRING
                 ACCESS  read-only
                 STATUS  mandatory
                 DESCRIPTION
                 "The rear LED cards that are installed on the chassis."
                 ::= { chassisTopology 52 }

     chassisRoom OBJECT-TYPE
                 SYNTAX  OCTET STRING (SIZE(0..24))
                 ACCESS read-write
                 STATUS mandatory
                 DESCRIPTION
                 "The name of the room where the chassis is located.
                 Maximum 23 characters for name plus NULL termination."
                 ::= { chassisTopology 53 }

     chassisName OBJECT-TYPE
                 SYNTAX  OCTET STRING (SIZE(0..16))
                 ACCESS read-write
                 STATUS mandatory
                 DESCRIPTION
                 "The name of the chassis.
                  Maximum 15 character long plus NULL termination."
                 ::= { chassisTopology 54 }

     chassisRack OBJECT-TYPE
                 SYNTAX  OCTET STRING (SIZE(0..24))
                 ACCESS read-write
                 STATUS mandatory
                 DESCRIPTION
                 "The name of the room where the chassis is located.
                 Maximum 23 characters for name plus NULL termination."
                 ::= { chassisTopology 55}

     chassisLowestU OBJECT-TYPE
                 SYNTAX  INTEGER
                 ACCESS read-write
                 STATUS mandatory
                 DESCRIPTION
                 "The lowest U position that is occupied in the rack."
                 ::= { chassisTopology 56}

     chassisUHeight OBJECT-TYPE
                 SYNTAX  INTEGER
                 ACCESS read-only
                 STATUS mandatory
                 DESCRIPTION
                 "The height of the chassis in 'U' units."
                 ::= { chassisTopology 57}

 -- ********************************************************************************
    managementModule OBJECT IDENTIFIER ::= { components 5 }
 -- ********************************************************************************

      mmStatusTable OBJECT-TYPE
                    SYNTAX  SEQUENCE OF MmStatusEntry
                    ACCESS  not-accessible
                    STATUS  mandatory
                    DESCRIPTION
                    "Table of the management module status."
                    ::= { managementModule 1 }

      mmStatusEntry OBJECT-TYPE
                    SYNTAX MmStatusEntry
                    ACCESS  not-accessible
                    STATUS  mandatory
                    DESCRIPTION
                    "Management module status entry."
                    INDEX { mmStatusIndex }
                    ::= { mmStatusTable 1 }

      MmStatusEntry ::= SEQUENCE {
                  mmStatusIndex INTEGER,
                  mmPresent INTEGER,
                  mmExtIpAddress IpAddress,
                  mmPrimary INTEGER,
                  mmHealthState INTEGER
                  }

      mmStatusIndex  OBJECT-TYPE
                  SYNTAX  INTEGER
                  ACCESS  read-only
                  STATUS  mandatory
                  DESCRIPTION
                  "Management module status index."
                  ::= { mmStatusEntry 1 }

      mmPresent  OBJECT-TYPE
                  SYNTAX  INTEGER {
                        no(0),
                        yes(1)
                  }
                  ACCESS  read-only
                  STATUS  mandatory
                  DESCRIPTION
                  "Management module current status."
                  ::= { mmStatusEntry 2 }

      mmExtIpAddress  OBJECT-TYPE
                  SYNTAX  IpAddress
                  ACCESS  read-only
                  STATUS  mandatory
                  DESCRIPTION
                  "Management module external IP address.

                  NOTE: The IPv6 addresses assigned to the MM may be viewed
                  with the extEthernetInterfaceIPv6 objects"
                  ::= { mmStatusEntry 3 }

      mmPrimary  OBJECT-TYPE
                  SYNTAX  INTEGER {
                        no(0),
                        yes(1)
                  }
                  ACCESS  read-only
                  STATUS  mandatory
                  DESCRIPTION
                  "Indicates if this Management module is a primary or not.
                  NOTE: If there is no standby MM, this value defaults to primary."
                  ::= { mmStatusEntry 4 }

      mmHealthState  OBJECT-TYPE
                  SYNTAX  INTEGER {
                        unknown(0),
                        good(1),
                        warning(2),
                        bad(3)
                  }
                  ACCESS  read-only
                  STATUS  mandatory
                  DESCRIPTION
                  "The health state for the management module.
                   0 = unknown, 1 = good, 2 = warning, 3 = bad."
                  ::= { mmStatusEntry 5 }

    -- ********************************************************************************
    -- IOM firmware image information 
    -- ********************************************************************************
    firmwareInformation  OBJECT IDENTIFIER ::= { components 8 }

      smFirmwareInformation  OBJECT IDENTIFIER ::= { firmwareInformation 1 }

          smFirmwareInfoTable OBJECT-TYPE
                      SYNTAX  SEQUENCE OF SmFirmwareInfoEntry
                      ACCESS  not-accessible
                      STATUS  mandatory
                      DESCRIPTION
                      "Switch Module firmware image information."
                      ::= { smFirmwareInformation 1 }

           smFirmwareInfoEntry  OBJECT-TYPE
                         SYNTAX SmFirmwareInfoEntry
                         ACCESS  not-accessible
                         STATUS  mandatory
                         DESCRIPTION
                         "Switch Module firmware image information table entry"
                         INDEX { smFirmwareInfoIndex }
                         ::= { smFirmwareInfoTable 1 }

           SmFirmwareInfoEntry ::= SEQUENCE {
                       smFirmwareInfoIndex INTEGER,
                       smFirmwareInfoModIndex INTEGER,
                       smFirmwareInfoImageIndex INTEGER,
                       smFirmwareInfoImageName OCTET STRING
                       }

           smFirmwareInfoIndex OBJECT-TYPE
                       SYNTAX  INTEGER
                       ACCESS  read-only
                       STATUS  mandatory
                       DESCRIPTION
                       "Sequence index in the firmware table."
                       ::= { smFirmwareInfoEntry 1 }

           smFirmwareInfoModIndex OBJECT-TYPE
                       SYNTAX  INTEGER
                       ACCESS  read-only
                       STATUS  mandatory
                       DESCRIPTION
                       "Switch Module number."
                       ::= { smFirmwareInfoEntry 2 }

           smFirmwareInfoImageIndex OBJECT-TYPE
                       SYNTAX  INTEGER
                       ACCESS  read-only
                       STATUS  mandatory
                       DESCRIPTION
                       "Switch Module firmware image index."
                       ::= { smFirmwareInfoEntry 3 }

           smFirmwareInfoImageName OBJECT-TYPE
                        SYNTAX  OCTET STRING
                        ACCESS  read-write
                        STATUS  mandatory
                        DESCRIPTION
                        "Switch Module firmware image name"
                        ::= { smFirmwareInfoEntry 4 }

    -- ********************************************************************************
    -- Firmware update for MM, Switch modules, and blades
    -- ********************************************************************************
    firmwareUpdate OBJECT IDENTIFIER ::= { components 9 }

    firmwareUpdateTarget        OBJECT-TYPE
                                SYNTAX  INTEGER {
                                  managementModule(0),
                                  switchModule1(11),
                                  switchModule2(12),
                                  switchModule3(13),
                                  switchModule4(14),
                                  unknown(255)
                                }
                                ACCESS  read-write
                                STATUS  mandatory
                                DESCRIPTION
                                "Target module whose firmware will be updated.
                                NOTE: Some switch modules do not allow firmware update.
                                When firmware update is attempted on those switch modules,
                                the agent will report an error."
                                ::= { firmwareUpdate 1 }

    firmwareUpdateTftpServer    OBJECT-TYPE
                                SYNTAX  OCTET STRING (SIZE(0..63))
                                ACCESS  read-write
                                STATUS  mandatory
                                DESCRIPTION
                                "If flashing via the legacy method using a tftp server, then
                                set the IP address or host name of the TFTP server where
                                the firmware file resides. The address must be entered in a
                                dotted decimal IP string (e.g. 9.37.44.2).

                                NOTE: IPv6 numeric addresses must be enclosed with brackets
                                (e.g. [fe80::5652:ff:fe50:53b6])."
                                ::= { firmwareUpdate 2 }

    firmwareUpdateFileName      OBJECT-TYPE
                                SYNTAX  OCTET STRING (SIZE(0..254))
                                ACCESS  read-write
                                STATUS  mandatory
                                DESCRIPTION
                                "File name of the firmware file."
                                ::= { firmwareUpdate 3 }

    firmwareUpdateStart         OBJECT-TYPE
                                SYNTAX INTEGER {
                                  execute(1),
                                  execute-with-reboot(2),
                                  execute-nowait(3),
                                  execute-with-reboot-nowait(4)
                                }
                                ACCESS  read-write
                                STATUS  mandatory
                                DESCRIPTION
                                "Start updating the firmware of the specified target module.
                                Using execute or execute-with-reboot will cause the SNMP client to
                                wait for the firmware update to complete.
                                Using execute-nowait or execute-with-reboot-nowait will not cause
                                the SNMP client to wait for the update to complete. Instead it will
                                flash the firmware in the background.

                                Note 1: If the execute-with-reboot or execute-with-reboot-nowait
                                option is selected, the target will reset after a successful flash.
                                This option is only valid if the firmwareUpdateTarget object is
                                set to managementModule.
                                Note 2: If flashing from a remote file, then both
                                firmwareUpdateServer and firmwareUpdateFileName must be
                                set. Otherwise if flashing via the legacy method using a tftp
                                server, then both firmwareUpdateTftpServer and
                                firmwareUpdateFileName must be set.
                                Note 3: Depending on the target, it might take up to several
                                minutes for the flash update to complete.  Do not reset the
                                target until the control has been returned.  At this point,
                                the results will be displayed.
                                Note 4: Use firmwareUpdateStatus to confirm the status of
                                the last firmware update initiated by SNMP method.  The
                                Management Module must be restarted for the new firmware to
                                take affect.
                                Note 5: If data encryption is currently enabled on this MM,
                                and you update the MM firmware to a level which does not
                                support data encryption, you will lose all your configuration
                                settings as a result.
                                Note 6: Since some I/O Module types use the MM TFTP server for
                                firmware file transfer during the firmware update process, the
                                tftpEnable MIB object must be set to enable prior to updating
                                the firmware for these modules.
                                Note 7: If IPv6 address(es) have been configured for one or more
                                interfaces/protocols/services on this MM, when you update
                                the firmware to a level which does not support IPv6, all IPv6
                                connectivity will be lost, and services/interfaces for which an IPv6
                                address was configured may not function properly. You will be required
                                to reconfigure these services/interfaces.

                                NOTE: Value returned for the GET command is meaningless
                                for this MIB object."
                                ::= { firmwareUpdate 4 }

    firmwareUpdateStatus        OBJECT-TYPE
                                SYNTAX OCTET STRING
                                ACCESS  read-only
                                STATUS  mandatory
                                DESCRIPTION
                                "Get the status of the last firmware update which was
                                initiated through SNMP method."
                                ::= { firmwareUpdate 5 }

    standbyFirmwareUpdateStatus  OBJECT-TYPE
                                 SYNTAX OCTET STRING
                                 ACCESS  read-only
                                 STATUS  mandatory
                                 DESCRIPTION
                                 "Get the current status of the firmware update for the standby MM.

                                 NOTE: This only applies to systems with a standby MM."
                                 ::= { firmwareUpdate 6 }

    firmwareImageNumber          OBJECT-TYPE
                                 SYNTAX INTEGER
                                 ACCESS  read-write
                                 STATUS  mandatory
                                 DESCRIPTION
                                 "If the module can upload more than one image, an image
                                 number must be specified after setting the firmware target.
                                 Please refer to the firmwareInformation section."
                                 ::= { firmwareUpdate 7 }

    firmwareActiveImage          OBJECT-TYPE
                                 SYNTAX INTEGER
                                 ACCESS  read-write
                                 STATUS  mandatory
                                 DESCRIPTION
                                 "If the module can upload more than one image, an active image
                                 number must be specified.  Please refer to the firmwareInformation section.
                                 NOTE: Value returned for the GET command is meaningless for this
                                 MIB object."
                                 ::= { firmwareUpdate 8 }

    firmwareUpdateServer         OBJECT-TYPE
                                 SYNTAX OCTET STRING (SIZE(0..254))
                                 ACCESS  read-write
                                 STATUS  mandatory
                                 DESCRIPTION
                                 "Contains the fully qualified remote location of the firmware
                                 packet file. Use firmwareUpdateFileName to specify the filename.

                                 A fully qualified remote location contains a supported
                                 protocol followed by a colon and two slashes (//), userid and
                                 password separated by a colon for login authentication, an
                                 @ sign, followed by the hostname or IP address of the
                                 server where the packet file resides, followed by an optional
                                 port number to the hostname, and the full pathname to the file.
                                 Note that if the port number is specified, it must be
                                 separated with the hostname (or IP address) by a colon.

                                 The MM currently supports the following protocols:
                                 TFTP, FTP, HTTP and HTTPS.

                                 The complete format of a fully qualified remote location is:

                                 <protocol>://<userid:password>@<hostname:port>/<pathname>

                                 An example of a fully qualified remote location can be:
                                       ftp://USERID:PASSW0RD@192.168.0.2:30045/tmp
                                 where the ftp protocol will be used for transferring the file in
                                 this location, username is USERID,  password is
                                 PASSW0RD, host IP address is 192.168.0.2, port number is
                                 30045, and the full pathname for the packet file is /tmp.

                                 and firmwareUpdateFileName is set to: cmefs.uxp

                                 Some protocols do not need the username, password, and
                                 the port number, so the minimum requirement for a fully
                                 qualified location can be:  <protocol>://<hostname>/<pathname>.

                                 Note: When updating certain switches via SFTP, only an RSA fingerprint 
                                 is supported. Please see your switch documentation for more information."
                                 ::= { firmwareUpdate 9 }

    -- ********************************************************************************
    -- Local file management
    -- ********************************************************************************
      fileManagement OBJECT IDENTIFIER ::= { components 11 }

       fileTopology OBJECT IDENTIFIER ::= { fileManagement 1 }

       currentDirectory OBJECT-TYPE
                  SYNTAX  OCTET STRING
                  ACCESS  read-write
                  STATUS  mandatory
                  DESCRIPTION
                  "Specifies the directory name for listing the requested files."
                  ::= { fileTopology 1 }

       fileDetailsTable OBJECT-TYPE
                    SYNTAX  SEQUENCE OF FileDetailsEntry
                    ACCESS  not-accessible
                    STATUS  mandatory
                    DESCRIPTION
                    "A table of all the files in the specified directory."
                    ::= { fileTopology 2 }

       fileDetailsEntry OBJECT-TYPE
                    SYNTAX FileDetailsEntry
                    ACCESS  not-accessible
                    STATUS  mandatory
                    DESCRIPTION
                    "File details entry."
                    INDEX { fileIndex }
                    ::= { fileDetailsTable 1 }

       FileDetailsEntry ::= SEQUENCE {
                   fileIndex INTEGER,
                   fileName OCTET STRING,
                   fileLastUpdate OCTET STRING,
                   fileSize OCTET STRING
                   }

       fileIndex  OBJECT-TYPE
                  SYNTAX  INTEGER
                  ACCESS  read-only
                  STATUS  mandatory
                  DESCRIPTION
                  "File sequence index."
                  ::= { fileDetailsEntry 1 }

       fileName  OBJECT-TYPE
                  SYNTAX  OCTET STRING
                  ACCESS  read-only
                  STATUS  mandatory
                  DESCRIPTION
                  "File name."
                  ::= { fileDetailsEntry 2 }

       fileLastUpdate  OBJECT-TYPE
                  SYNTAX  OCTET STRING
                  ACCESS  read-only
                  STATUS  mandatory
                  DESCRIPTION
                  "Date of the latest file update."
                  ::= { fileDetailsEntry 3 }

       fileSize  OBJECT-TYPE
                  SYNTAX  OCTET STRING
                  ACCESS  read-only
                  STATUS  mandatory
                  DESCRIPTION
                  "File size in bytes."
                  ::= { fileDetailsEntry 4 }

       fileManagementCmd OBJECT-TYPE
                  SYNTAX  OCTET STRING
                  ACCESS  read-write
                  STATUS  mandatory
                  DESCRIPTION
                  "This field will execute the selected operations on the files.
                   The following operation is supported:
                   DEL name     -   delete a file

                   Examples:
                    - to delete the file named switch.config in tftproot directory
                    set the value to 'DEL tftproot/switch.config'

                  NOTE: Value returned for the GET command is meaningless for this
                  MIB object."
                  ::= { fileManagement 3 }

       fileSystemSpaceAvailable OBJECT-TYPE
                  SYNTAX  OCTET STRING
                  ACCESS  read-only
                  STATUS  mandatory
                  DESCRIPTION
                  "This field displays the available space of the MM file system."
                  ::= { fileManagement 6 }

    -- ********************************************************************************
    -- Chassis discovery
    -- ********************************************************************************
      cmeRemoteChassis OBJECT IDENTIFIER ::= { components 12 }

      cmeRemoteChassisTable OBJECT-TYPE
                     SYNTAX  SEQUENCE OF CmeRemoteChassisEntry
                     ACCESS  not-accessible
                     STATUS  mandatory
                     DESCRIPTION
                     "This table is used to provide the discovered MMs based on the new, 
                      extended SLP response information."
                     ::= { cmeRemoteChassis 1 }

       cmeRemoteChassisEntry OBJECT-TYPE
                     SYNTAX CmeRemoteChassisEntry
                     ACCESS  not-accessible
                     STATUS  mandatory
                     DESCRIPTION
                     "Remote chassis entry"
                     INDEX { cmeRemoteChassisIndex }
                     ::= { cmeRemoteChassisTable 1 }

       CmeRemoteChassisEntry ::= SEQUENCE {
                   cmeRemoteChassisIndex INTEGER,
                   cmeSystemName OCTET STRING,
                   cmeType OCTET STRING,
                   cmeSerial OCTET STRING,
                   cmeFru OCTET STRING,
                   cmeUuid OCTET STRING,
                   cmeSlot OCTET STRING,
                   cmeMidPid OCTET STRING,
                   cmeMacAddress OCTET STRING,
                   cmeChassisSerial OCTET STRING,
                   cmeChassisFru OCTET STRING,
                   cmeChassisMachineTypeMode OCTET STRING,
                   cmeSystemStatus INTEGER,
                   cmeChassisUuid OCTET STRING,
                   cmeChassisMidPid OCTET STRING,
                   cmeChassisId OCTET STRING, 
                   cmeChassisLocation OCTET STRING,
                   cmeChassisRoomId OCTET STRING, 
                   cmeChassisRackId OCTET STRING,
                   cmeChassisUser OCTET STRING,
                   cmeChassisFruList OCTET STRING,
                   cmeFirmwareVersion OCTET STRING,
                   cmeChassisType OCTET STRING,
                   cmeIpv4Status INTEGER,
                   cmeIpv4Addresses OCTET STRING,
                   cmeIpv4AddressesFloat OCTET STRING,
                   cmeIpv4Protocols OCTET STRING,
                   cmeIpv6Status INTEGER,
                   cmeIpv6Addresses OCTET STRING,
                   cmeIpv6AddressesFloat OCTET STRING,
                   cmeIpv6Protocols OCTET STRING
                   }

      cmeRemoteChassisIndex  OBJECT-TYPE
                   SYNTAX  INTEGER
                   ACCESS  read-only
                   STATUS  mandatory
                   DESCRIPTION
                   "Remote chassis discovery sequence index."
                   ::= { cmeRemoteChassisEntry 1 }
                   
     cmeSystemName OBJECT-TYPE
                   SYNTAX  OCTET STRING
                   ACCESS  read-only
                   STATUS  mandatory
                   DESCRIPTION
                   "System name for this discovery management module."
                   ::= { cmeRemoteChassisEntry 2 }
                   
      cmeType       OBJECT-TYPE
                   SYNTAX  OCTET STRING
                   ACCESS  read-only
                   STATUS  mandatory
                   DESCRIPTION
                   "Management module service processor type."
                   ::= { cmeRemoteChassisEntry 3}

      cmeSerial     OBJECT-TYPE
                   SYNTAX  OCTET STRING
                   ACCESS  read-only
                   STATUS  mandatory
                   DESCRIPTION
                   "Management module serial number."
                   ::= { cmeRemoteChassisEntry 4 }

      cmeFru        OBJECT-TYPE
                   SYNTAX  OCTET STRING
                   ACCESS  read-only
                   STATUS  mandatory
                   DESCRIPTION
                   "Management module Field-Replaceable number."
                   ::= { cmeRemoteChassisEntry 5 }

      cmeUuid            OBJECT-TYPE
                      SYNTAX  OCTET STRING
                      ACCESS  read-only
                      STATUS  mandatory
                      DESCRIPTION
                      "Management module UUID."
                      ::= { cmeRemoteChassisEntry 6}
                      
      cmeSlot           OBJECT-TYPE
                      SYNTAX  OCTET STRING
                      ACCESS  read-only
                      STATUS  mandatory
                      DESCRIPTION
                      "Management module slot."
                      ::= { cmeRemoteChassisEntry 7}
                      
      cmeMidPid           OBJECT-TYPE
                      SYNTAX  OCTET STRING
                      ACCESS  read-only
                      STATUS  mandatory
                      DESCRIPTION
                      "Management module Mid-plane Pid."
                      ::= { cmeRemoteChassisEntry 8} 
                      
      cmeMacAddress           OBJECT-TYPE
                      SYNTAX  OCTET STRING
                      ACCESS  read-only
                      STATUS  mandatory
                      DESCRIPTION
                      "Management module MAC address."
                      ::= { cmeRemoteChassisEntry 9} 
                                                    
      cmeChassisSerial OBJECT-TYPE
                   SYNTAX  OCTET STRING
                   ACCESS  read-only
                   STATUS  mandatory
                   DESCRIPTION
                   "Chassis serial number."
                   ::= { cmeRemoteChassisEntry 10 }

      cmeChassisFru OBJECT-TYPE
                   SYNTAX  OCTET STRING
                   ACCESS  read-only
                   STATUS  mandatory
                   DESCRIPTION
                   "Chassis Field-Replaceable number."
                   ::= { cmeRemoteChassisEntry 11 }

      cmeChassisMachineTypeMode OBJECT-TYPE
                   SYNTAX  OCTET STRING
                   ACCESS  read-only
                   STATUS  mandatory
                   DESCRIPTION
                   "Chassis machine type and model number."
                   ::= { cmeRemoteChassisEntry 12 }
                   
      cmeSystemStatus OBJECT-TYPE
                   SYNTAX  INTEGER {
                        critical(0),
                        non-Critical(2),
                        system-Level(4),
                        unknown(9),
                        noResponse(170),
                        normal(255)
                   }
                   ACCESS  read-only
                   STATUS  mandatory
                   DESCRIPTION
                   "Chassis status."
                   ::= { cmeRemoteChassisEntry 13 }
                   
      cmeChassisUuid OBJECT-TYPE
                   SYNTAX  OCTET STRING
                   ACCESS  read-only
                   STATUS  mandatory
                   DESCRIPTION
                   "Chassis UUID."
                   ::= { cmeRemoteChassisEntry 14 }
                   
      cmeChassisMidPid OBJECT-TYPE
                   SYNTAX  OCTET STRING
                   ACCESS  read-only
                   STATUS  mandatory
                   DESCRIPTION
                   "Chassis mid-plane ID."
                   ::= { cmeRemoteChassisEntry 15}
                   
      cmeChassisId OBJECT-TYPE
                   SYNTAX  OCTET STRING
                   ACCESS  read-only
                   STATUS  mandatory
                   DESCRIPTION
                   "Chassis ID."
                   ::= { cmeRemoteChassisEntry 16}
                   
       cmeChassisLocation OBJECT-TYPE
                   SYNTAX  OCTET STRING
                   ACCESS  read-only
                   STATUS  mandatory
                   DESCRIPTION
                   "Chassis location information."
                   ::= { cmeRemoteChassisEntry 17 }  
                     
       cmeChassisRoomId OBJECT-TYPE
                   SYNTAX  OCTET STRING
                   ACCESS  read-only
                   STATUS  mandatory
                   DESCRIPTION
                   "Chassis room ID."
                   ::= { cmeRemoteChassisEntry 18 }  
                    
       cmeChassisRackId OBJECT-TYPE
                   SYNTAX  OCTET STRING
                   ACCESS  read-only
                   STATUS  mandatory
                   DESCRIPTION
                   "Chassis rack ID."
                   ::= { cmeRemoteChassisEntry 19 }  
                   
       cmeChassisUser OBJECT-TYPE
                   SYNTAX  OCTET STRING
                   ACCESS  read-only
                   STATUS  mandatory
                   DESCRIPTION
                   "Chassis user information."
                   ::= { cmeRemoteChassisEntry 20 } 
                     
       cmeChassisFruList OBJECT-TYPE
                   SYNTAX  OCTET STRING
                   ACCESS  read-only
                   STATUS  mandatory
                   DESCRIPTION
                   "Chassis FRU list."
                   ::= { cmeRemoteChassisEntry 21 }   
                                                          
       cmeFirmwareVersion OBJECT-TYPE
                   SYNTAX  OCTET STRING
                   ACCESS  read-only
                   STATUS  mandatory
                   DESCRIPTION
                   "Firmware version of the discovery management module."
                   ::= { cmeRemoteChassisEntry 22 }
                     
       cmeChassisType OBJECT-TYPE
                   SYNTAX  OCTET STRING
                   ACCESS  read-only
                   STATUS  mandatory
                   DESCRIPTION
                   "Chassis type."
                   ::= { cmeRemoteChassisEntry 23 }  
                                               
       cmeIpv4Status OBJECT-TYPE
                   SYNTAX  INTEGER {
                        disabled(0),
                        enabled(1)
                   }
                   ACCESS  read-only
                   STATUS  mandatory
                   DESCRIPTION
                   "A flag to state if IPv4 is enabled"
                   ::= { cmeRemoteChassisEntry 24 }
                   
        cmeIpv4Addresses  OBJECT-TYPE
                   SYNTAX  OCTET STRING
                   ACCESS  read-only
                   STATUS  mandatory
                   DESCRIPTION
                   "The IPv4 addresses configured for the chassis."
                   ::= { cmeRemoteChassisEntry 25 }
                   
        cmeIpv4AddressesFloat OBJECT-TYPE
                   SYNTAX  OCTET STRING
                   ACCESS  read-only
                   STATUS  mandatory
                   DESCRIPTION
                   "The floating IPv4 addresses configured for the chassis."
                   ::= { cmeRemoteChassisEntry 26 }
                   
        cmeIpv4Protocols  OBJECT-TYPE
                   SYNTAX  OCTET STRING
                   ACCESS  read-only
                   STATUS  mandatory
                   DESCRIPTION
                   "The IPv4 protocols configured for the chassis."
                   ::= { cmeRemoteChassisEntry 27 }
          
        cmeIpv6Status OBJECT-TYPE
                   SYNTAX  INTEGER {
                        disabled(0),
                        enabled(1)
                   }
                   ACCESS  read-only
                   STATUS  mandatory
                   DESCRIPTION
                   "A flag to state if IPv6 is enabled"
                   ::= { cmeRemoteChassisEntry 28 }
                   
        cmeIpv6Addresses  OBJECT-TYPE
                   SYNTAX  OCTET STRING
                   ACCESS  read-only
                   STATUS  mandatory
                   DESCRIPTION
                   "The IPv6 addresses configured for the chassis."
                   ::= { cmeRemoteChassisEntry 29 }
                   
        cmeIpv6AddressesFloat OBJECT-TYPE
                   SYNTAX  OCTET STRING
                   ACCESS  read-only
                   STATUS  mandatory
                   DESCRIPTION
                   "The floating IPv6 addresses configured for the chassis."
                   ::= { cmeRemoteChassisEntry 30}
                   
        cmeIpv6Protocols  OBJECT-TYPE
                   SYNTAX  OCTET STRING
                   ACCESS  read-only
                   STATUS  mandatory
                   DESCRIPTION
                   "The IPv6 protocols configured for the chassis."
                   ::= { cmeRemoteChassisEntry 31 }

        chassisDiscovery OBJECT-TYPE
                    SYNTAX INTEGER{
                       execute(1)
                    }
                    ACCESS read-write
                    STATUS mandatory
                    DESCRIPTION
                    "Discovery of remote Chassis.
                    NOTE: Value returned for the GET command is meaningless for this MIB object."
                    ::= { cmeRemoteChassis 2}

    -- ********************************************************************************
    -- componentPower
    -- ********************************************************************************
    componentPower OBJECT IDENTIFIER ::= { components 31 }
      -- component power/restart control

      -- ********************************************************************************
      -- componentPowerTable
      -- ********************************************************************************
      componentPowerTable OBJECT-TYPE
                     SYNTAX  SEQUENCE OF ComponentPowerEntry
                     ACCESS  not-accessible
                     STATUS  mandatory
                     DESCRIPTION
                     "Table of component remote power control information.
                     Contains power on/off enablement status for each component."
                     ::= { componentPower 1 }

       componentPowerEntry OBJECT-TYPE
                     SYNTAX ComponentPowerEntry
                     ACCESS  not-accessible
                     STATUS  mandatory
                     DESCRIPTION
                     "Component power/restart table entry"
                     INDEX { componentPowerTopologyPath }
                     ::= { componentPowerTable 1 }

       ComponentPowerEntry ::= SEQUENCE {
                   componentPowerTopologyPath OCTET STRING,
                   componentPowerName OCTET STRING,
                   componentPowerState INTEGER,
                   componentPowerAction INTEGER,
                   componentPowerEnableSMSBootMenu INTEGER
                   }

       componentPowerTopologyPath  OBJECT-TYPE
                   SYNTAX  OCTET STRING  (SIZE (0..100))
                   ACCESS  read-only
                   STATUS  mandatory
                   DESCRIPTION
                   "The unique identifier for a component in this table. The chassis and each
                    installed component is represented by a hardware topology tree, where
                    each node in the tree represents a component. The path to a particular
                    component consists of one or more <component>,<instance> pairs, where
                    each successive pair is a child of the previous parent pair.

                    As an example, the root of the tree is the chassis and is represented
                    by the pair 'CHASSIS, 1'. This pair indicates the first instance of
                    the chassis. If a blade is inserted in slot 4 of the chassis, its
                    topology path is 'CHASSIS, 1, BLADE, 4'. With this format, the
                    components in the chassis can be determined along with their relative
                    hierarchy to each other.

                    This component table is indexed by this unique topology
                    path and the numeric designations for the components are:

                     CHASSIS,                0x01   Chassis
                     MM,                     0x02   Management Module
                     BLADE,                  0x03   Main system board of a blade
                     POWER,                  0x04   Power Supply, Power Module, etc
                     COOLING,                0x05   Fan, blower, or other cooling device
                     IO_MODULE,              0x06   Has I/O interface, i.e. - switch or bridge
                     MEDIA,                  0x07   Media device
                     PROCESSOR,              0x08   Any processor, processor module, etc
                     STORAGE,                0x09   Any type of storage device
                     EXPANSION,              0x0A   Expansion Card (not covered by more specific type)
                     MEMORY,                 0x0B   Any memory device, module, etc
                     MFRU,                   0x0C   Managed FRU Device
                     PANEL,                  0x0D   Any sort of panel device, such as a front panel
                     BLADE_EXPANSION_MODULE, 0x0E   Expansion option (BEM) such as PEU, BSE, etc
                     CARD_EXPANSION,         0x0F   Expansion card, ie. daughter card
                     CARD_HS_EXPANSION,      0x10   High Speed Expansion card, ie. daughter card
                     INTERPOSER,             0x11   Interposer device
                     CLOCK,                  0x12   Clock card
                     MUX,                    0x13   Mulitplexer card
                     ADDIN,                  0x14   cKVM card & other addin cards
                     STORAGE_MODULE,         0x15   Container of one or more Storage Devices
                     SYS_EXPANSION_CARD,     0x16   Management card
                     BATTERY,                0x17   A single battery
                     BATTERY_MODULE,         0x18   Container of one or more batteries
                     REAR_LED,               0x19   Rear LED card
                     MEMORY_BANK,            0x1A   Memory banks
                     AIR_FILTER,             0x1B   Filter mechanism (bezel)
                     SERIAL_PORT_MODULE,     0x1C   Container of one or more serial ports
                     PARENT,                 0x1D   Reference to parent for multi-parent support
                     PHY_PORT,               0x1E   Physical port
                     IO_EXPANDER,            0x1F   RAID card
                     CABLE,                  0x20   Cable/Interconnect
                     FAN_MUX                 0x29   Fan multiplexer card
                     PCI_EXPRESS,            0x32   PCI express card on (PEN)
                     FLASH_DIMM,             0x33   Used for SPD devices that matches the silkscreen of the DIMM slot
                     RACK,                   0x50   Rack
                     PLATFORM,               0x51   Generic Platform like rack mounted server/appliance
                     DATAPLEX,               0x52   DataPlex
                     OTHER,                  0x53   Other unknown etc.
                     PERIPHERAL_MODULE,      0x54 
                     SYSTEM_BOARD,           0x55   System board
                     PROCESSOR_MODULE,       0x56 
                     BACK_PANEL,             0x57 
                     POWER_SYSTEM_BOARD,     0x58 
                     STORAGE_BACKPLANE,      0x59   Drive back plane
                     PROC_BOARD,             0x5A   Holds 1 or more processors
                     POWER_DI,               0x5B   Power mgt / power distribution board
                     CHASSIS_BACK_PANEL,     0x5C 
                     SUB_CHASSIS,            0x5D 
                     OTHER_CHASSIS_BOARD,    0x5E 
                     DEVICE_MODULE,          0x5F 
                     REMOTE_DEVICE,          0x60   Remote mgt communication device
                     EXTERNAL_ENVIRONMENT,   0x61   Such as external temp sensor for outside box temps
                     PROC_MEMORY_MODULE,     0x62   Processors and memory on same module"
                   ::= { componentPowerEntry 1 }

       componentPowerName OBJECT-TYPE
                   SYNTAX  OCTET STRING
                   ACCESS  read-only
                   STATUS  mandatory
                   DESCRIPTION
                   "The name of the component as a null terminated string."
                   ::= { componentPowerEntry 2 }

       componentPowerState OBJECT-TYPE
                   SYNTAX  INTEGER {
                     off(0),
                     on(1),
                     standby(3),
                     hibernate(4),
                     unknown(255)
                   }
                   ACCESS  read-only
                   STATUS  mandatory
                   DESCRIPTION
                   "Indicates the power state of the component specified.
                    If the state cannot be determined, the unknown(255) is returned."
                   ::= { componentPowerEntry 3 }

       componentPowerAction OBJECT-TYPE
                   SYNTAX  INTEGER {
                     none(0),
                     off(1),
                     on(2),
                     softoff(3),
                     restart(4),
                     restartSysMgmtProcessor(5),
                     restartNMI(6)
                   }
                   ACCESS  read-write
                   STATUS  mandatory
                   DESCRIPTION
                   "Control the power state of a specific component.

                   none:     No action, value returned for GET.
                   off:      Power-off component.
                   on:       Power-on component.

                   softoff:  Shutdown OS and power-off component. This
                             operation is not supported on all components.

                   restart:  Restart a component.

                   restartSysMgmtProcessor:
                             Restart a component's system management processor.

                   restartNMI:
                             Issue a NMI (Non-Maskable Interrupt) restart to
                             the component. This option is not supported on all
                             components.

                   NOTE: Value returned for the GET command is meaningless
                   for this MIB object. The componentPowerState MIB object should be
                   used to check the power state of the component(s)"
                   ::= { componentPowerEntry 4 }

       componentPowerEnableSMSBootMenu OBJECT-TYPE
                   SYNTAX  INTEGER { disable(0), enable(1) }
                   ACCESS  read-write
                   STATUS  mandatory
                   DESCRIPTION
                   "Enables/disables a component restart to the SMS boot menu.
                   Setting this object to 'enable(1)' will cause a reboot of 
                   the node to the SMS menu.
                   This option is not supported by all components, and at the time 
                   of this MIB definition was only supported on POWER blades."
                   ::= { componentPowerEntry 5 }


      -- ********************************************************************************
      -- componentPowerTableCacheTimeout
      -- ********************************************************************************
       componentPowerTableCacheTimeout OBJECT-TYPE
                   SYNTAX  INTEGER
                   ACCESS  read-only
                   STATUS  mandatory
                   DESCRIPTION
                   "The timeout value (in seconds) of the cached data for the
                   table, componentPowerTable.
                   This value is static (constant) and cannot be set."
                   ::= { componentPower 2 }


      -- ********************************************************************************
      -- componentPowerDetailsTable
      -- ********************************************************************************
      componentPowerDetailsTable OBJECT-TYPE
                     SYNTAX  SEQUENCE OF ComponentPowerDetailsEntry
                     ACCESS  not-accessible
                     STATUS  mandatory
                     DESCRIPTION
                     "Table of component power detail information."
                     ::= { componentPower 6 }

       componentPowerDetailsEntry OBJECT-TYPE
                     SYNTAX ComponentPowerDetailsEntry
                     ACCESS  not-accessible
                     STATUS  mandatory
                     DESCRIPTION
                     "Component power Details table entry"
                     INDEX { componentPowerDetailsTopologyPath }
                     ::= { componentPowerDetailsTable 1 }

       ComponentPowerDetailsEntry ::= SEQUENCE {
                   componentPowerDetailsTopologyPath OCTET STRING,
                   componentPowerDetailsName OCTET STRING,
                   componentPowerDetailsMaxPowerConfig INTEGER,
                   componentPowerDetailsEffectiveClockRate OCTET STRING,
                   componentPowerDetailsMaximumClockRate OCTET STRING,
                   componentPowerDetailsPowerSaverMode INTEGER,
                   componentPowerDetailsDynamicPowerSaver INTEGER,
                   componentPowerDetailsDynamicPowerFavorPerformanceOverPower INTEGER,
                   componentPowerDetailsPowerControl INTEGER,
                   componentPowerDetailsPcapMin OCTET STRING,
                   componentPowerDetailsPcapGuaranteedMin OCTET STRING,
                   componentPowerDetailsPcapMax OCTET STRING,
                   componentPowerDetailsStaticCap OCTET STRING,
                   componentPowerDetailsRuntimeCap OCTET STRING
                   }

       componentPowerDetailsTopologyPath  OBJECT-TYPE
                   SYNTAX  OCTET STRING  (SIZE (0..100))
                   ACCESS  read-only
                   STATUS  mandatory
                   DESCRIPTION
                   "The unique identifier for a component in this table. The chassis and each
                    installed component is represented by a hardware topology tree, where
                    each node in the tree represents a component. The path to a particular
                    component consists of one or more <component>,<instance> pairs, where
                    each successive pair is a child of the previous parent pair.

                    As an example, the root of the tree is the chassis and is represented
                    by the pair 'CHASSIS, 1'. This pair indicates the first instance of
                    the chassis. If a blade is inserted in slot 4 of the chassis, its
                    topology path is 'CHASSIS, 1, BLADE, 4'. With this format, the
                    components in the chassis can be determined along with their relative
                    hierarchy to each other.

                    This component table is indexed by this unique topology
                    path and the numeric designations for the components are:

                     CHASSIS,                0x01   Chassis
                     MM,                     0x02   Management Module
                     BLADE,                  0x03   Main system board of a blade
                     POWER,                  0x04   Power Supply, Power Module, etc
                     COOLING,                0x05   Fan, blower, or other cooling device
                     IO_MODULE,              0x06   Has I/O interface, i.e. - switch or bridge
                     MEDIA,                  0x07   Media device
                     PROCESSOR,              0x08   Any processor, processor module, etc
                     STORAGE,                0x09   Any type of storage device
                     EXPANSION,              0x0A   Expansion Card (not covered by more specific type)
                     MEMORY,                 0x0B   Any memory device, module, etc
                     MFRU,                   0x0C   Managed FRU Device
                     PANEL,                  0x0D   Any sort of panel device, such as a front panel
                     BLADE_EXPANSION_MODULE, 0x0E   Expansion option (BEM) such as PEU, BSE, etc
                     CARD_EXPANSION,         0x0F   Expansion card, ie. daughter card
                     CARD_HS_EXPANSION,      0x10   High Speed Expansion card, ie. daughter card
                     INTERPOSER,             0x11   Interposer device
                     CLOCK,                  0x12   Clock card
                     MUX,                    0x13   Mulitplexer card
                     ADDIN,                  0x14   cKVM card & other addin cards
                     STORAGE_MODULE,         0x15   Container of one or more Storage Devices
                     SYS_EXPANSION_CARD,     0x16   Management card
                     BATTERY,                0x17   A single battery
                     BATTERY_MODULE,         0x18   Container of one or more batteries
                     REAR_LED,               0x19   Rear LED card
                     MEMORY_BANK,            0x1A   Memory banks
                     AIR_FILTER,             0x1B   Filter mechanism (bezel)
                     SERIAL_PORT_MODULE,     0x1C   Container of one or more serial ports
                     PARENT,                 0x1D   Reference to parent for multi-parent support
                     PHY_PORT,               0x1E   Physical port
                     IO_EXPANDER,            0x1F   RAID card
                     CABLE,                  0x20   Cable/Interconnect
                     FAN_MUX                 0x29   Fan multiplexer card
                     PCI_EXPRESS,            0x32   PCI express card on (PEN)
                     FLASH_DIMM,             0x33   Used for SPD devices that matches the silkscreen of the DIMM slot
                     RACK,                   0x50   Rack
                     PLATFORM,               0x51   Generic Platform like rack mounted server/appliance
                     DATAPLEX,               0x52   DataPlex
                     OTHER,                  0x53   Other unknown etc.
                     PERIPHERAL_MODULE,      0x54 
                     SYSTEM_BOARD,           0x55   System board
                     PROCESSOR_MODULE,       0x56 
                     BACK_PANEL,             0x57 
                     POWER_SYSTEM_BOARD,     0x58 
                     STORAGE_BACKPLANE,      0x59   Drive back plane
                     PROC_BOARD,             0x5A   Holds 1 or more processors
                     POWER_DI,               0x5B   Power mgt / power distribution board
                     CHASSIS_BACK_PANEL,     0x5C 
                     SUB_CHASSIS,            0x5D 
                     OTHER_CHASSIS_BOARD,    0x5E 
                     DEVICE_MODULE,          0x5F 
                     REMOTE_DEVICE,          0x60   Remote mgt communication device
                     EXTERNAL_ENVIRONMENT,   0x61   Such as external temp sensor for outside box temps
                     PROC_MEMORY_MODULE,     0x62   Processors and memory on same module"
                   ::= { componentPowerDetailsEntry 1 }

       componentPowerDetailsName OBJECT-TYPE
                   SYNTAX  OCTET STRING
                   ACCESS  read-only
                   STATUS  mandatory
                   DESCRIPTION
                   "The name of the component as a null terminated string."
                   ::= { componentPowerDetailsEntry 2 }

       componentPowerDetailsMaxPowerConfig  OBJECT-TYPE
                 SYNTAX  INTEGER
                 ACCESS  read-write
                 STATUS  mandatory
                 DESCRIPTION
                 "Component Module Details Table Maximum Power Configuration.
                 Allow the user to set the maximum power that can be used by the component. This
                 function is also known as power capping.
                 Component must be powered on to set this value.

                 If the value of maximum power config is zero, it means the component doesn't
                 support the power capping feature"
                 ::= { componentPowerDetailsEntry 3 }

       componentPowerDetailsEffectiveClockRate  OBJECT-TYPE
                 SYNTAX  OCTET STRING
                 ACCESS  read-only
                 STATUS  mandatory
                 DESCRIPTION
                 "Component Module Details Table Effective CPU Clock Rate applies to DPM
                 components only.  It displays processor's effective clock rate based
                 on sample interval.  Note that some components do not effective
                 clock rate.  In this case, 'notApplicable' will be displayed.

                 NOTE: The effective clock rate are reported only on a primary slot when
                 a server component spans multiple slots (e.g. double wide or
                 triple wide).  For example if the component is double wide and
                 is installed in slot 3 and 4.  3 is primary slot while 4 is not.
                 The effective clock rate are reported on slot 3 while 'notApplicable'
                 is displayed for slot 4."
                 ::= { componentPowerDetailsEntry 4 }

       componentPowerDetailsMaximumClockRate  OBJECT-TYPE
                 SYNTAX  OCTET STRING
                 ACCESS  read-only
                 STATUS  mandatory
                 DESCRIPTION
                 "Component Module Details Table Maximum CPU Clock Rate applies to DPM
                 components only.  It displays processor's maximum clock rate based
                 on sample interval.  Note that some components do not maximum
                 clock rate.  In this case, 'notApplicable' will be displayed.

                 NOTE: The maximum clock rate are reported only on a primary slot when
                 a server components spans multiple slots (e.g. double wide or
                 triple wide).  For example if the component is double wide and
                 is installed in slot 3 and 4.  3 is primary slot while 4 is not.
                 The maximum clock rate are reported on slot 3 while 'notApplicable'
                 is displayed for slot 4."
                 ::= { componentPowerDetailsEntry 5 }

       componentPowerDetailsPowerSaverMode OBJECT-TYPE
                 SYNTAX  INTEGER {
                         disable(0),
                         enable(1),
                         notApplicable(255)
                 }
                 ACCESS  read-write
                 STATUS  mandatory
                 DESCRIPTION
                 "When enabled, the static low power saver mode allows the component to selectively
                 alter its operating voltage and frequency to reduce power consumption.
                 This feature is not available on all component types.  Please refer to the component documentation for details.
                 If a component does not support the static low power saver mode, this object will return notApplicable (255).

                 Under certain rare circumstances, the enabling of the static low power saver mode
                 may not complete successfully due to interactions with other
                 component functions, such as BIOS. Therefore, it is highly recommended that
                 the user perform a GET of this object after performing a SET, in order
                 to verify the completion of the intended operation.

                 NOTE: enabling this object will disable componentPowerDetailsDynamicPowerSaver if its not already disabled."
                 ::= { componentPowerDetailsEntry 6 }

       componentPowerDetailsDynamicPowerSaver OBJECT-TYPE
                 SYNTAX  INTEGER {
                         disable(0),
                         enable(1),
                         notApplicable(255)
                 }
                 ACCESS  read-write
                 STATUS  mandatory
                 DESCRIPTION
                 "When enabled, Dynamic Power Saver allows the voltage and frequency of the CPUs on the component
                 to be controlled based on how busy the CPU is.  This feature is not available on all component types.
                 Please refer to the component documentation for details.  If a component does not support the dynamic power
                 saver, this object will return notApplicable (255).

                 Under certain rare circumstances, the enabling of the dynamic power saver may not complete
                 successfully due to interactions with other component functions, such as BIOS. Therefore, it is
                 highly recommended that the user perform a GET of this object after performing a SET, in order
                 to verify the completion of the intended operation.

                 NOTE: enabling this object will disable componentPowerDetailsPowerSaverMode if its not already disabled."
                 ::= { componentPowerDetailsEntry 7 }

       componentPowerDetailsDynamicPowerFavorPerformanceOverPower OBJECT-TYPE
                 SYNTAX  INTEGER {
                         disable(0),
                         enable(1),
                         notApplicable(255)
                 }
                 ACCESS  read-write
                 STATUS  mandatory
                 DESCRIPTION
                 "When enabled, Dynamic Power Favor Performance Over Power supports a max performance mode that pushes the
                 system past its nominal CPU frequency when CPU and memory utilization implies it would help and the
                 system allows it.  Dynamic Power Performance Over Power can be active on the component only after Dynamic
                 Power Saver is enabled.  This feature is not available on all components types.  Please refer to the
                 component documentation for details.  If a component does not support the dynamic power saver, this object
                 will return notApplicable (255).

                 Under certain rare circumstances, the enabling of the dynamic power favor performance over power
                 may not complete successfully due to interactions with other component functions, such as BIOS.
                 Therefore, it is highly recommended that the user perform a GET of this object after performing a SET,
                 in order to verify the completion of the intended operation."
                 ::= { componentPowerDetailsEntry 8 }

       componentPowerDetailsPowerControl OBJECT-TYPE
                 SYNTAX  INTEGER {
                         none(0),
                         measurement(1),
                         measurementpcap(2),
                         psave(3),
                         measurementpsave(4),
                         measurementpcappsave(5),
                         notApplicable(255)
                 }
                 ACCESS  read-write
                 STATUS  mandatory
                 DESCRIPTION
                 "This object is used to get or set the power control setting on a component.

                 If dynamic power mgmt is not supported on a component, notApplicable(255) will be returned.

                 This will set the power control setting on all slots of the multiwide component. The
                 same can be used if the component is single wide."
                 ::= { componentPowerDetailsEntry 9 }

       componentPowerDetailsPcapMin  OBJECT-TYPE
                 SYNTAX  OCTET STRING
                 ACCESS  read-only
                 STATUS  mandatory
                 DESCRIPTION
                 "Component Module Details Table power capping Minimum value in watts.
                 The component must support the advanced power management feature.

                 If the value of Pcap Min is 'notApplicable', it means the component doesn't
                 support the power capping feature.

                 If the value of Pcap Min is 'notAvailable', it means the data
                 could not be obtained."
                 ::= { componentPowerDetailsEntry 10 }

       componentPowerDetailsPcapGuaranteedMin  OBJECT-TYPE
                 SYNTAX  OCTET STRING
                 ACCESS  read-only
                 STATUS  mandatory
                 DESCRIPTION
                 "Component Module Details Table power capping Guaranteed Minimum value in watts.
                 The component must support the advanced power management feature.

                 If the value of Pcap Guaranteed Min is 'notApplicable', it means the component doesn't
                 support the power capping feature.

                 If the value of Pcap GuaranteedMin is 'notAvailable', it means the data
                 could not be obtained."
                 ::= { componentPowerDetailsEntry 11 }

       componentPowerDetailsPcapMax  OBJECT-TYPE
                 SYNTAX  OCTET STRING
                 ACCESS  read-only
                 STATUS  mandatory
                 DESCRIPTION
                 "Component Module Details Table power capping Maximum value in watts.
                 The component must support the advanced power management feature.

                 If the value is '<max1> Watts,<max2> Watts', which means,
                 - if componentPowerDetailsDynamicPowerSaver is enabled, it is <max2>
                 - otherwise it is <max1>

                 If the value of Pcap Max is 'notApplicable', it means the component doesn't
                 support the power capping feature.

                 If the value of Pcap Min is 'notAvailable', it means the data
                 could not be obtained."
                 ::= { componentPowerDetailsEntry 12 }

       componentPowerDetailsStaticCap  OBJECT-TYPE
                 SYNTAX  OCTET STRING
                 ACCESS  read-only
                 STATUS  mandatory
                 DESCRIPTION
                 "Component Module Details Table static capabilities list.
                 This is a list of five power management capabilities that the component
                 may or may not support.  The list of power management capabilities is as follow:

                         Power Measurement
                         Power Capping
                         Power Saving
                         Dynamic Power Saving
                         Extended Dynamic Power Saving

                 The returned octet string contains 5 pairs of numeric characters separated by
                 blank characters.  Each of these pairs will consist of either '00' or '01'.
                 '00' indicates that the capability is not there, '01' indicates that the capability
                 is present on the component.

                 The 5 pairs represent the capabilities of the 5 types listed above, in order,
                 for this component in the table.

                 Example response:  '01 01 00 00 00'
                 This component has the capability of Power Management and Power Capping, but does not
                 support the last three types."
                 ::= { componentPowerDetailsEntry 13 }

       componentPowerDetailsRuntimeCap  OBJECT-TYPE
                 SYNTAX  OCTET STRING
                 ACCESS  read-only
                 STATUS  mandatory
                 DESCRIPTION
                 "Component Module Details Table run-time capabilities list.
                 If the component supports the capability as indicated in the static capability information,
                 the user has the ability to enable or disable that function and this table reflects that configuration.

                 The power management capabilites for the run-time list is as follows:

                         Power Measurement
                         Power Capping
                         Power Saving
                         Dynamic Power Saving
                         Extended Dynamic Power Saving

                 The returned octet string contains 5 pairs of numeric characters separated by
                 blank characters.  Each of these pairs will consist of either '00' or '01'.
                 '00' indicates that the capability is currently not available, '01' indicates that
                 the capability is currently available.

                 The 5 pairs represent the current capabilities of the 5 types listed above, in order,
                 for this component in the table.

                 Example response:  '01 00 00 00 00'
                 This component has the capability of Power Management only. The current state of the
                 component does not support the remaining 4 capabiites at this time."
                 ::= { componentPowerDetailsEntry 14 }

      -- *************************************************************************
      -- componentPowerDetailsTableCacheTimeout
      -- *************************************************************************
      componentPowerDetailsTableCacheTimeout OBJECT-TYPE
                   SYNTAX  INTEGER
                   ACCESS  read-only
                   STATUS  mandatory
                   DESCRIPTION
                   "The timeout value (in seconds) of the cached data for the
                   table, componentPowerDetailsTable.
                   This value is static (constant) and cannot be set."
                     ::= { componentPower 7 }

    -- ********************************************************************************
    -- componentConfiguration
    -- ********************************************************************************
    componentConfiguration OBJECT IDENTIFIER ::= { components 32 }
      -- component configuration control

      -- ********************************************************************************
      -- componentBayDataTable
      -- ********************************************************************************
      componentBayDataTable OBJECT-TYPE
                     SYNTAX  SEQUENCE OF ComponentBayDataEntry
                     ACCESS  not-accessible
                     STATUS  mandatory
                     DESCRIPTION
                     "Table of component bay User data information.
                     Contains user provided data for each component bay."
                     ::= { componentConfiguration 1 }

       componentBayDataEntry OBJECT-TYPE
                     SYNTAX ComponentBayDataEntry
                     ACCESS  not-accessible
                     STATUS  mandatory
                     DESCRIPTION
                     "Component Bay Data table entry"
                     INDEX { componentBayDataTopologyPath }
                     ::= { componentBayDataTable 1 }

       ComponentBayDataEntry ::= SEQUENCE {
                   componentBayDataTopologyPath OCTET STRING,
                   componentBayDataName OCTET STRING,
                   componentBayDataStatus INTEGER,
                   componentBayData OCTET STRING
                   }

       componentBayDataTopologyPath  OBJECT-TYPE
                   SYNTAX  OCTET STRING  (SIZE (0..100))
                   ACCESS  read-only
                   STATUS  mandatory
                   DESCRIPTION
                   "The unique identifier for a component in this table. The chassis and each
                    installed component is represented by a hardware topology tree, where
                    each node in the tree represents a component. The path to a particular
                    component consists of one or more <component>,<instance> pairs, where
                    each successive pair is a child of the previous parent pair.

                    As an example, the root of the tree is the chassis and is represented
                    by the pair 'CHASSIS, 1'. This pair indicates the first instance of
                    the chassis. If a blade is inserted in slot 4 of the chassis, its
                    topology path is 'CHASSIS, 1, BLADE, 4'. With this format, the
                    components in the chassis can be determined along with their relative
                    hierarchy to each other.

                    This component table is indexed by this unique topology
                    path and the numeric designations for the components are:

                     CHASSIS,                0x01   Chassis
                     MM,                     0x02   Management Module
                     BLADE,                  0x03   Main system board of a blade
                     POWER,                  0x04   Power Supply, Power Module, etc
                     COOLING,                0x05   Fan, blower, or other cooling device
                     IO_MODULE,              0x06   Has I/O interface, i.e. - switch or bridge
                     MEDIA,                  0x07   Media device
                     PROCESSOR,              0x08   Any processor, processor module, etc
                     STORAGE,                0x09   Any type of storage device
                     EXPANSION,              0x0A   Expansion Card (not covered by more specific type)
                     MEMORY,                 0x0B   Any memory device, module, etc
                     MFRU,                   0x0C   Managed FRU Device
                     PANEL,                  0x0D   Any sort of panel device, such as a front panel
                     BLADE_EXPANSION_MODULE, 0x0E   Expansion option (BEM) such as PEU, BSE, etc
                     CARD_EXPANSION,         0x0F   Expansion card, ie. daughter card
                     CARD_HS_EXPANSION,      0x10   High Speed Expansion card, ie. daughter card
                     INTERPOSER,             0x11   Interposer device
                     CLOCK,                  0x12   Clock card
                     MUX,                    0x13   Mulitplexer card
                     ADDIN,                  0x14   cKVM card & other addin cards
                     STORAGE_MODULE,         0x15   Container of one or more Storage Devices
                     SYS_EXPANSION_CARD,     0x16   Management card
                     BATTERY,                0x17   A single battery
                     BATTERY_MODULE,         0x18   Container of one or more batteries
                     REAR_LED,               0x19   Rear LED card
                     MEMORY_BANK,            0x1A   Memory banks
                     AIR_FILTER,             0x1B   Filter mechanism (bezel)
                     SERIAL_PORT_MODULE,     0x1C   Container of one or more serial ports
                     PARENT,                 0x1D   Reference to parent for multi-parent support
                     PHY_PORT,               0x1E   Physical port
                     IO_EXPANDER,            0x1F   RAID card
                     CABLE,                  0x20   Cable/Interconnect
                     FAN_MUX                 0x29   Fan multiplexer card
                     PCI_EXPRESS,            0x32   PCI express card on (PEN)
                     FLASH_DIMM,             0x33   Used for SPD devices that matches the silkscreen of the DIMM slot
                     RACK,                   0x50   Rack
                     PLATFORM,               0x51   Generic Platform like rack mounted server/appliance
                     DATAPLEX,               0x52   DataPlex
                     OTHER,                  0x53   Other unknown etc.
                     PERIPHERAL_MODULE,      0x54 
                     SYSTEM_BOARD,           0x55   System board
                     PROCESSOR_MODULE,       0x56 
                     BACK_PANEL,             0x57 
                     POWER_SYSTEM_BOARD,     0x58 
                     STORAGE_BACKPLANE,      0x59   Drive back plane
                     PROC_BOARD,             0x5A   Holds 1 or more processors
                     POWER_DI,               0x5B   Power mgt / power distribution board
                     CHASSIS_BACK_PANEL,     0x5C 
                     SUB_CHASSIS,            0x5D 
                     OTHER_CHASSIS_BOARD,    0x5E 
                     DEVICE_MODULE,          0x5F 
                     REMOTE_DEVICE,          0x60   Remote mgt communication device
                     EXTERNAL_ENVIRONMENT,   0x61   Such as external temp sensor for outside box temps
                     PROC_MEMORY_MODULE,     0x62   Processors and memory on same module"
                   ::= { componentBayDataEntry 1 }

       componentBayDataName OBJECT-TYPE
                   SYNTAX  OCTET STRING
                   ACCESS  read-only
                   STATUS  mandatory
                   DESCRIPTION
                   "The name of the component as a null terminated string."
                   ::= { componentBayDataEntry 2 }

       componentBayDataStatus OBJECT-TYPE
                   SYNTAX  INTEGER {
                     supported(0),
                     bsmp(1),
                     notPresent(2),
                     discovering(3),
                     notApplicable(255)
                   }
                   ACCESS  read-only
                   STATUS  mandatory
                   DESCRIPTION
                   "This shows Bay Data (BD) Status. 
                    0 means the component fully supports BD.
                    1 means that the component's BIOS does not support BD.
                    2 means that there is no component in the bay.
                    3 means that the component is being discovered.
                    255 means that the component does not support BBD."
                   ::= { componentBayDataEntry 3 }

       componentBayData OBJECT-TYPE
                   SYNTAX  OCTET STRING (SIZE (0..60))
                   ACCESS  read-write
                   STATUS  mandatory
                   DESCRIPTION
                   "A null terminated string that defines the component Bay Data.
                    This data is puched to the components's BSMP and SMBIOS structures,
                    where it can be used by the components's OS.  Up to 60 characters can
                    be defined plus a Null terminator."
                   ::= { componentBayDataEntry 4 }

      -- *************************************************************************
      -- componentBayDataTableCacheTimeout
      -- *************************************************************************
      componentBayDataTableCacheTimeout OBJECT-TYPE
                   SYNTAX  INTEGER
                   ACCESS  read-only
                   STATUS  mandatory
                   DESCRIPTION
                   "The timeout value (in seconds) of the cached data for the
                   table, componentBayDataTable.
                   This value is static (constant) and cannot be set."
                     ::= { componentConfiguration 2 }

      -- ********************************************************************************
      -- componentEthOverUSBInterfaceTable
      -- ********************************************************************************
         componentEthOverUSBInterfaceTable OBJECT-TYPE
                     SYNTAX  SEQUENCE OF ComponentEthOverUSBInterfaceEntry
                     ACCESS  not-accessible
                     STATUS  mandatory
                     DESCRIPTION
                     "Table of blade Service Processor's Ethernet over USB interface."
                     ::= { componentConfiguration 6 }

         componentEthOverUSBInterfaceEntry OBJECT-TYPE
                    SYNTAX  ComponentEthOverUSBInterfaceEntry
                    ACCESS  not-accessible
                    STATUS  mandatory
                    DESCRIPTION
                    "Blade Service Processor's Ethernet over USB interface entry."
                    INDEX { componentEthOverUSBInterfaceTopologyPath }
                    ::= { componentEthOverUSBInterfaceTable 1 }

         ComponentEthOverUSBInterfaceEntry ::= SEQUENCE {
                  componentEthOverUSBInterfaceTopologyPath OCTET STRING,
                  componentEthOverUSBInterfaceName OCTET STRING,
                  componentEthOverUSBInterfaceEnable INTEGER
                  }

         componentEthOverUSBInterfaceTopologyPath  OBJECT-TYPE
                   SYNTAX  OCTET STRING  (SIZE (0..100))
                   ACCESS  read-only
                   STATUS  mandatory
                   DESCRIPTION
                   "The unique identifier for a component in this table. The chassis and each
                    installed component is represented by a hardware topology tree, where
                    each node in the tree represents a component. The path to a particular
                    component consists of one or more <component>,<instance> pairs, where
                    each successive pair is a child of the previous parent pair.

                    As an example, the root of the tree is the chassis and is represented
                    by the pair 'CHASSIS, 1'. This pair indicates the first instance of
                    the chassis. If a blade is inserted in slot 4 of the chassis, its
                    topology path is 'CHASSIS, 1, BLADE, 4'. With this format, the
                    components in the chassis can be determined along with their relative
                    hierarchy to each other.

                    This component table is indexed by this unique topology
                    path and the numeric designations for the components are:

                     CHASSIS,                0x01   Chassis
                     MM,                     0x02   Management Module
                     BLADE,                  0x03   Main system board of a blade
                     POWER,                  0x04   Power Supply, Power Module, etc
                     COOLING,                0x05   Fan, blower, or other cooling device
                     IO_MODULE,              0x06   Has I/O interface, i.e. - switch or bridge
                     MEDIA,                  0x07   Media device
                     PROCESSOR,              0x08   Any processor, processor module, etc
                     STORAGE,                0x09   Any type of storage device
                     EXPANSION,              0x0A   Expansion Card (not covered by more specific type)
                     MEMORY,                 0x0B   Any memory device, module, etc
                     MFRU,                   0x0C   Managed FRU Device
                     PANEL,                  0x0D   Any sort of panel device, such as a front panel
                     BLADE_EXPANSION_MODULE, 0x0E   Expansion option (BEM) such as PEU, BSE, etc
                     CARD_EXPANSION,         0x0F   Expansion card, ie. daughter card
                     CARD_HS_EXPANSION,      0x10   High Speed Expansion card, ie. daughter card
                     INTERPOSER,             0x11   Interposer device
                     CLOCK,                  0x12   Clock card
                     MUX,                    0x13   Mulitplexer card
                     ADDIN,                  0x14   cKVM card & other addin cards
                     STORAGE_MODULE,         0x15   Container of one or more Storage Devices
                     SYS_EXPANSION_CARD,     0x16   Management card
                     BATTERY,                0x17   A single battery
                     BATTERY_MODULE,         0x18   Container of one or more batteries
                     REAR_LED,               0x19   Rear LED card
                     MEMORY_BANK,            0x1A   Memory banks
                     AIR_FILTER,             0x1B   Filter mechanism (bezel)
                     SERIAL_PORT_MODULE,     0x1C   Container of one or more serial ports
                     PARENT,                 0x1D   Reference to parent for multi-parent support
                     PHY_PORT,               0x1E   Physical port
                     IO_EXPANDER,            0x1F   RAID card
                     CABLE,                  0x20   Cable/Interconnect
                     FAN_MUX                 0x29   Fan multiplexer card
                     PCI_EXPRESS,            0x32   PCI express card on (PEN)
                     FLASH_DIMM,             0x33   Used for SPD devices that matches the silkscreen of the DIMM slot
                     RACK,                   0x50   Rack
                     PLATFORM,               0x51   Generic Platform like rack mounted server/appliance
                     DATAPLEX,               0x52   DataPlex
                     OTHER,                  0x53   Other unknown etc.
                     PERIPHERAL_MODULE,      0x54 
                     SYSTEM_BOARD,           0x55   System board
                     PROCESSOR_MODULE,       0x56 
                     BACK_PANEL,             0x57 
                     POWER_SYSTEM_BOARD,     0x58 
                     STORAGE_BACKPLANE,      0x59   Drive back plane
                     PROC_BOARD,             0x5A   Holds 1 or more processors
                     POWER_DI,               0x5B   Power mgt / power distribution board
                     CHASSIS_BACK_PANEL,     0x5C 
                     SUB_CHASSIS,            0x5D 
                     OTHER_CHASSIS_BOARD,    0x5E 
                     DEVICE_MODULE,          0x5F 
                     REMOTE_DEVICE,          0x60   Remote mgt communication device
                     EXTERNAL_ENVIRONMENT,   0x61   Such as external temp sensor for outside box temps
                     PROC_MEMORY_MODULE,     0x62   Processors and memory on same module"
                   ::= { componentEthOverUSBInterfaceEntry 1 }
       

         componentEthOverUSBInterfaceName OBJECT-TYPE
                  SYNTAX  OCTET STRING
                  ACCESS  read-only
                  STATUS  mandatory
                  DESCRIPTION
                  "The name of the component as a null terminated string."
                  ::= { componentEthOverUSBInterfaceEntry 2 }

         componentEthOverUSBInterfaceEnable OBJECT-TYPE
                  SYNTAX  INTEGER {
                    disabled(0),
                    enabled(1),
                    notApplicable(255)
                  }
                  ACCESS  read-write
                  STATUS  mandatory
                  DESCRIPTION
                  "This object allows the user to view the status of, and enable
                  or disable, a component's interface on Ethernet-over-USB.

                  NOTE: If the component either does not exist or does not support
                  Ethernet-over-USB command interface. It displays 'notApplicable'.

                  NOTE: It will take about 10 or more seconds for the disable/enable
                  setting to take effect."
                  ::= { componentEthOverUSBInterfaceEntry 3 }


      -- *************************************************************************
      -- componentEthOverUSBInterfaceTableCacheTimeout
      -- *************************************************************************
      componentEthOverUSBInterfaceTableCacheTimeout OBJECT-TYPE
                   SYNTAX  INTEGER
                   ACCESS  read-only
                   STATUS  mandatory
                   DESCRIPTION
                   "The timeout value (in seconds) of the cached data for the
                   table, componentEthOverUSBInterfaceTable.
                   This value is static (constant) and cannot be set."
                     ::= {  componentConfiguration 7 }


      -- ********************************************************************************
      -- componentConfigurationTable
      -- ********************************************************************************
      componentConfigurationTable OBJECT-TYPE
                    SYNTAX  SEQUENCE OF ComponentConfigurationEntry
                    ACCESS  not-accessible
                    STATUS  mandatory
                    DESCRIPTION
                    "Table of component configuration information."
                    ::= { componentConfiguration 11 }

      componentConfigurationEntry OBJECT-TYPE
                    SYNTAX ComponentConfigurationEntry
                    ACCESS  not-accessible
                    STATUS  mandatory
                    DESCRIPTION
                    "Component configuration table entry"
                    INDEX { componentConfigurationTopologyPath }
                    ::= { componentConfigurationTable 1 }

      ComponentConfigurationEntry ::= SEQUENCE {
                  componentConfigurationTopologyPath OCTET STRING,
                  componentConfigurationName OCTET STRING,
                  componentConfigurationActiveBootMode INTEGER,
                  componentConfigurationPendingBootMode INTEGER,
                  componentConfigurationAutoPowerOn INTEGER,
                  componentConfigurationPowerOnRestartDelay INTEGER,
                  componentConfigurationLocalPowerControlEnable INTEGER,
                  componentConfigurationWakeOnLanControlEnable INTEGER
                  }

      componentConfigurationTopologyPath  OBJECT-TYPE
                  SYNTAX  OCTET STRING  (SIZE (0..100))
                  ACCESS  read-only
                  STATUS  mandatory
                  DESCRIPTION
                  "The unique identifier for a component in this table. The chassis and each
                   installed component is represented by a hardware topology tree, where
                   each node in the tree represents a component. The path to a particular
                   component consists of one or more <component>,<instance> pairs, where
                   each successive pair is a child of the previous parent pair.

                   As an example, the root of the tree is the chassis and is represented
                   by the pair 'CHASSIS, 1'. This pair indicates the first instance of
                   the chassis. If a blade is inserted in slot 4 of the chassis, its
                   topology path is 'CHASSIS, 1, BLADE, 4'. With this format, the
                   components in the chassis can be determined along with their relative
                   hierarchy to each other.

                   This component table is indexed by this unique topology
                   path and the numeric designations for the components are:

                    CHASSIS,                0x01   Chassis
                    MM,                     0x02   Management Module
                    BLADE,                  0x03   Main system board of a blade
                    POWER,                  0x04   Power Supply, Power Module, etc
                    COOLING,                0x05   Fan, blower, or other cooling device
                    IO_MODULE,              0x06   Has I/O interface, i.e. - switch or bridge
                    MEDIA,                  0x07   Media device
                    PROCESSOR,              0x08   Any processor, processor module, etc
                    STORAGE,                0x09   Any type of storage device
                    EXPANSION,              0x0A   Expansion Card (not covered by more specific type)
                    MEMORY,                 0x0B   Any memory device, module, etc
                    MFRU,                   0x0C   Managed FRU Device
                    PANEL,                  0x0D   Any sort of panel device, such as a front panel
                    BLADE_EXPANSION_MODULE, 0x0E   Expansion option (BEM) such as PEU, BSE, etc
                    CARD_EXPANSION,         0x0F   Expansion card, ie. daughter card
                    CARD_HS_EXPANSION,      0x10   High Speed Expansion card, ie. daughter card
                    INTERPOSER,             0x11   Interposer device
                    CLOCK,                  0x12   Clock card
                    MUX,                    0x13   Mulitplexer card
                    ADDIN,                  0x14   cKVM card & other addin cards
                    STORAGE_MODULE,         0x15   Container of one or more Storage Devices
                    SYS_EXPANSION_CARD,     0x16   Management card
                    BATTERY,                0x17   A single battery
                    BATTERY_MODULE,         0x18   Container of one or more batteries
                    REAR_LED,               0x19   Rear LED card
                    MEMORY_BANK,            0x1A   Memory banks
                    AIR_FILTER,             0x1B   Filter mechanism (bezel)
                    SERIAL_PORT_MODULE,     0x1C   Container of one or more serial ports
                    PARENT,                 0x1D   Reference to parent for multi-parent support
                    PHY_PORT,               0x1E   Physical port
                    IO_EXPANDER,            0x1F   RAID card
                    CABLE,                  0x20   Cable/Interconnect
                    FAN_MUX                 0x29   Fan multiplexer card
                     PCI_EXPRESS,            0x32   PCI express card on (PEN)
                     FLASH_DIMM,             0x33   Used for SPD devices that matches the silkscreen of the DIMM slot
                     RACK,                   0x50   Rack
                     PLATFORM,               0x51   Generic Platform like rack mounted server/appliance
                     DATAPLEX,               0x52   DataPlex
                     OTHER,                  0x53   Other unknown etc.
                     PERIPHERAL_MODULE,      0x54 
                     SYSTEM_BOARD,           0x55   System board
                     PROCESSOR_MODULE,       0x56 
                     BACK_PANEL,             0x57 
                     POWER_SYSTEM_BOARD,     0x58 
                     STORAGE_BACKPLANE,      0x59   Drive back plane
                     PROC_BOARD,             0x5A   Holds 1 or more processors
                     POWER_DI,               0x5B   Power mgt / power distribution board
                     CHASSIS_BACK_PANEL,     0x5C 
                     SUB_CHASSIS,            0x5D 
                     OTHER_CHASSIS_BOARD,    0x5E 
                     DEVICE_MODULE,          0x5F 
                     REMOTE_DEVICE,          0x60   Remote mgt communication device
                     EXTERNAL_ENVIRONMENT,   0x61   Such as external temp sensor for outside box temps
                     PROC_MEMORY_MODULE,     0x62   Processors and memory on same module"
                  ::= { componentConfigurationEntry 1 }

      componentConfigurationName OBJECT-TYPE
                  SYNTAX  OCTET STRING
                  ACCESS  read-write
                  STATUS  mandatory
                  DESCRIPTION
                  "The name of the component as a null terminated string.
                  This object is configurable."
                  ::= { componentConfigurationEntry 2 }

      componentConfigurationActiveBootMode OBJECT-TYPE
                  SYNTAX  INTEGER {
                       temporary(1),
                       permanent(2),
                       notApplicable(255)
                  }
                  ACCESS  read-only
                  STATUS  mandatory
                  DESCRIPTION
                  "Indicates the active copy of the firmware from which the component is booting.
                  NOTE: Some components do not support the automatic boot recovery. It displays
                  'notApplicable' for such components.
                  Booting from the temporary copy is recommended since it typically contains the
                  latest enhancements and fixes. Switching to the permanent copy should be reserved
                  for when booting from the temporary copy is no longer possible."
                  ::= { componentConfigurationEntry 3 }

      componentConfigurationPendingBootMode OBJECT-TYPE
                  SYNTAX  INTEGER {
                    temporary(1),
                    permanent(2),
                    notApplicable(255)
                  }
                  ACCESS  read-write
                  STATUS  mandatory
                  DESCRIPTION
                  "Indicates the copy of the firmware from which the component will boot
                  after the next reboot.
                  NOTE: Some components do not support the automatic boot recovery. It displays
                  'notApplicable' for such components and the value can not be set.
                  Booting from the temporary copy is recommended since it typically contains the
                  latest enhancements and fixes. Switching to the permanent copy should be reserved
                  for when booting from the temporary copy is no longer possible."
                  ::= { componentConfigurationEntry 4 }

      componentConfigurationAutoPowerOn OBJECT-TYPE
                  SYNTAX  INTEGER {
                    restore(1),
                    auto(2),
                    manual(3),
                    notApplicable(255)
                  }
                  ACCESS  read-write
                  STATUS  mandatory
                  DESCRIPTION
                  "Component auto-power on policy.
                    - restore: component will be powered on which were previously on.
                    - auto:    component will automatically be powered on when power is applied to the chassis.
                    - manual:  component will be left off until manually powered on by the user.
                    - notApplicable: is a read-only value, this value cannot be set."
                  ::= { componentConfigurationEntry 5 }

      componentConfigurationPowerOnRestartDelay OBJECT-TYPE
                  SYNTAX  INTEGER (0..32767)
                  ACCESS  read-write
                  STATUS  mandatory
                  DESCRIPTION
                  "Restart delay (in seconds) when power is applied to a component."
                  ::= { componentConfigurationEntry 6 }

      componentConfigurationLocalPowerControlEnable OBJECT-TYPE
                     SYNTAX  INTEGER {
                       disabled(0),
                       enabled(1),
                       notApplicable(255)
                     }
                     ACCESS  read-write
                     STATUS  mandatory
                     DESCRIPTION
                     "Component local power control enablement status."
                     ::= { componentConfigurationEntry 7 }

      componentConfigurationWakeOnLanControlEnable OBJECT-TYPE
                     SYNTAX  INTEGER {
                       disabled(0),
                       enabled(1),
                       notApplicable(255)
                     }
                     ACCESS  read-write
                     STATUS  mandatory
                     DESCRIPTION
                     "Component Wake On LAN enablement status.
                     If WOL is not supported by the component, it displays 'notApplicable'
                     and WOL can not be enabled or disabled."
                     ::= { componentConfigurationEntry 8 }

      -- *************************************************************************
      -- componentConfigurationTableCacheTimeout
      -- *************************************************************************
      componentConfigurationTableCacheTimeout OBJECT-TYPE
                   SYNTAX  INTEGER
                   ACCESS  read-only
                   STATUS  mandatory
                   DESCRIPTION
                   "The timeout value (in seconds) of the cached data for the
                   table, componentConfigurationTable.
                   This value is static (constant) and cannot be set."
                    ::= { componentConfiguration 12 }


      -- ********************************************************************************
      -- componentNetworkConfiguration
      -- ********************************************************************************
      componentNetworkConfiguration  OBJECT IDENTIFIER ::= { componentConfiguration 16 }

        componentIPv4ConfigTable OBJECT-TYPE
                       SYNTAX  SEQUENCE OF ComponentIPv4ConfigEntry
                       ACCESS  not-accessible
                       STATUS  mandatory
                       DESCRIPTION
                       "Table of all components' network interfaces."
                       ::= { componentNetworkConfiguration 1 }

         componentIPv4ConfigEntry OBJECT-TYPE
                       SYNTAX  ComponentIPv4ConfigEntry
                       ACCESS  not-accessible
                       STATUS  mandatory
                       DESCRIPTION
                       "Component configuration table entry"
                       INDEX { componentIPv4ConfigTopologyPath, componentIPv4ConfigPortIndex }
                       ::= { componentIPv4ConfigTable 1 }

         ComponentIPv4ConfigEntry ::= SEQUENCE {
                     componentIPv4ConfigTopologyPath OCTET STRING,
                     componentIPv4ConfigPortIndex INTEGER,
                     componentIPv4ConfigName OCTET STRING,
                     componentIPv4ConfigPortLabel OCTET STRING,
                     componentIPv4ConfigPhysicalLinkStatus INTEGER,
                     componentIPv4ConfigPhysicalLinkState INTEGER,
                     componentIPv4ConfigIPAddr IpAddress,
                     componentIPv4ConfigSubnetMask IpAddress,
                     componentIPv4ConfigGatewayAddr IpAddress,
                     componentIPv4ConfigVlanId INTEGER,
                     componentIPv4ConfigDHCPEnable INTEGER,
                     componentIPv4ConfigMACAddr OCTET STRING
                     }

         componentIPv4ConfigTopologyPath  OBJECT-TYPE
                   SYNTAX  OCTET STRING  (SIZE (0..100))
                   ACCESS  read-only
                   STATUS  mandatory
                   DESCRIPTION
                   "The unique identifier for a component in this table. The chassis and each
                    installed component is represented by a hardware topology tree, where
                    each node in the tree represents a component. The path to a particular
                    component consists of one or more <component>,<instance> pairs, where
                    each successive pair is a child of the previous parent pair.

                    As an example, the root of the tree is the chassis and is represented
                    by the pair 'CHASSIS, 1'. This pair indicates the first instance of
                    the chassis. If a blade is inserted in slot 4 of the chassis, its
                    topology path is 'CHASSIS, 1, BLADE, 4'. With this format, the
                    components in the chassis can be determined along with their relative
                    hierarchy to each other.

                    Note that this TP is preceded by a single octet that specifies the TP length.
                    This is required since this table is indexed with two indices and, therefore,
                    the TP length must be explicitly provided.

                    This component table is indexed by this unique topology
                    path and the numeric designations for the components are:

                     CHASSIS,                0x01   Chassis
                     MM,                     0x02   Management Module
                     BLADE,                  0x03   Main system board of a blade
                     POWER,                  0x04   Power Supply, Power Module, etc
                     COOLING,                0x05   Fan, blower, or other cooling device
                     IO_MODULE,              0x06   Has I/O interface, i.e. - switch or bridge
                     MEDIA,                  0x07   Media device
                     PROCESSOR,              0x08   Any processor, processor module, etc
                     STORAGE,                0x09   Any type of storage device
                     EXPANSION,              0x0A   Expansion Card (not covered by more specific type)
                     MEMORY,                 0x0B   Any memory device, module, etc
                     MFRU,                   0x0C   Managed FRU Device
                     PANEL,                  0x0D   Any sort of panel device, such as a front panel
                     BLADE_EXPANSION_MODULE, 0x0E   Expansion option (BEM) such as PEU, BSE, etc
                     CARD_EXPANSION,         0x0F   Expansion card, ie. daughter card
                     CARD_HS_EXPANSION,      0x10   High Speed Expansion card, ie. daughter card
                     INTERPOSER,             0x11   Interposer device
                     CLOCK,                  0x12   Clock card
                     MUX,                    0x13   Mulitplexer card
                     ADDIN,                  0x14   cKVM card & other addin cards
                     STORAGE_MODULE,         0x15   Container of one or more Storage Devices
                     SYS_EXPANSION_CARD,     0x16   Management card
                     BATTERY,                0x17   A single battery
                     BATTERY_MODULE,         0x18   Container of one or more batteries
                     REAR_LED,               0x19   Rear LED card
                     MEMORY_BANK,            0x1A   Memory banks
                     AIR_FILTER,             0x1B   Filter mechanism (bezel)
                     SERIAL_PORT_MODULE,     0x1C   Container of one or more serial ports
                     PARENT,                 0x1D   Reference to parent for multi-parent support
                     PHY_PORT,               0x1E   Physical port
                     IO_EXPANDER,            0x1F   RAID card
                     CABLE,                  0x20   Cable/Interconnect
                     FAN_MUX                 0x29   Fan multiplexer card
                     PCI_EXPRESS,            0x32   PCI express card on (PEN)
                     FLASH_DIMM,             0x33   Used for SPD devices that matches the silkscreen of the DIMM slot
                     RACK,                   0x50   Rack
                     PLATFORM,               0x51   Generic Platform like rack mounted server/appliance
                     DATAPLEX,               0x52   DataPlex
                     OTHER,                  0x53   Other unknown etc.
                     PERIPHERAL_MODULE,      0x54 
                     SYSTEM_BOARD,           0x55   System board
                     PROCESSOR_MODULE,       0x56 
                     BACK_PANEL,             0x57 
                     POWER_SYSTEM_BOARD,     0x58 
                     STORAGE_BACKPLANE,      0x59   Drive back plane
                     PROC_BOARD,             0x5A   Holds 1 or more processors
                     POWER_DI,               0x5B   Power mgt / power distribution board
                     CHASSIS_BACK_PANEL,     0x5C 
                     SUB_CHASSIS,            0x5D 
                     OTHER_CHASSIS_BOARD,    0x5E 
                     DEVICE_MODULE,          0x5F 
                     REMOTE_DEVICE,          0x60   Remote mgt communication device
                     EXTERNAL_ENVIRONMENT,   0x61   Such as external temp sensor for outside box temps
                     PROC_MEMORY_MODULE,     0x62   Processors and memory on same module"
                   ::= { componentIPv4ConfigEntry 1 }

         componentIPv4ConfigPortIndex OBJECT-TYPE
                     SYNTAX  INTEGER
                     ACCESS  read-only
                     STATUS  mandatory
                     DESCRIPTION
                     "The physical port number of the given entry."
                     ::= { componentIPv4ConfigEntry 2 }

         componentIPv4ConfigName OBJECT-TYPE
                     SYNTAX  OCTET STRING
                     ACCESS  read-only
                     STATUS  mandatory
                     DESCRIPTION
                     "The name of the component as a null terminated string."
                     ::= { componentIPv4ConfigEntry 3 }

         componentIPv4ConfigPortLabel OBJECT-TYPE
                     SYNTAX  OCTET STRING
                     ACCESS  read-only
                     STATUS  mandatory
                     DESCRIPTION
                     "Show string label that identifies the interface."
                     ::= { componentIPv4ConfigEntry 4 }

         componentIPv4ConfigPhysicalLinkStatus OBJECT-TYPE
                     SYNTAX  INTEGER {
                       down(0),
                       up(1),
                       notApplicable(255)
                     }
                     ACCESS  read-only
                     STATUS  mandatory
                     DESCRIPTION
                     "Indicates whether this network interface port is up or down.
                     If this network interface doesn't support up/down, show
                     'notApplicable(255)'."
                     ::= { componentIPv4ConfigEntry 5 }

         componentIPv4ConfigPhysicalLinkState OBJECT-TYPE
                     SYNTAX  INTEGER {
                       down(0),
                       up(1),
                       loopback(2),
                       notApplicable(255)
                     }
                     ACCESS  read-write
                     STATUS  mandatory
                     DESCRIPTION
                     "Configuration object for requesting the physical port
                     to be either, down(0), up(1) or loopback(2). To get the
                     current status of a physical port, use the object,
                     componentIPv4ConfigPhysicalLinkStatus.
                     If this network interface doesn't support up/down/loopback,
                     show 'notApplicable(255)'."
                     ::= { componentIPv4ConfigEntry 6 }

         componentIPv4ConfigIPAddr OBJECT-TYPE
                     SYNTAX  IpAddress
                     ACCESS  read-write
                     STATUS  mandatory
                     DESCRIPTION
                     "Show/modify current IP address of the component network
                     interface.  Note that only if the
                     componentIPv4ConfigPhysicalLinkStatus is 'up(1)' and the
                     componentIPv4ConfigDHCPEnable is not 'useDhcp(1)', should the
                     IP address be pushed down to component System Management
                     Processor."
                     ::= { componentIPv4ConfigEntry 7 }

         componentIPv4ConfigSubnetMask OBJECT-TYPE
                     SYNTAX  IpAddress
                     ACCESS  read-write
                     STATUS  mandatory
                     DESCRIPTION
                     "Show or modifie current subnet mask of the component network
                     interface.  Note that only if the
                     componentIPv4ConfigPhysicalLinkStatus is 'up(1)' and the
                     componentIPv4ConfigDHCPEnable is not 'useDhcp(1)', should the
                     IP address be pushed down to component System Management
                     Processor."
                     ::= { componentIPv4ConfigEntry 8 }

         componentIPv4ConfigGatewayAddr OBJECT-TYPE
                     SYNTAX  IpAddress
                     ACCESS  read-write
                     STATUS  mandatory
                     DESCRIPTION
                     "Show or modify current IP gateway of the component network
                     interface.  Note that only if the
                     componentIPv4ConfigPhysicalLinkStatus is 'up(1)' and the
                     componentIPv4ConfigDHCPEnable is not 'useDhcp(1)', should the
                     IP address be pushed down to component System Management
                     Processor."
                     ::= { componentIPv4ConfigEntry 9 }

         componentIPv4ConfigVlanId   OBJECT-TYPE
                     SYNTAX  INTEGER
                      ACCESS  read-write
                      STATUS  mandatory
                      DESCRIPTION
                      "This is the Virtual LAN ID for supported network
                      interface cards (NICs).  The range of valid VLAN ID's
                      is 0 to 4095."
                      ::= { componentIPv4ConfigEntry 10 }

         componentIPv4ConfigDHCPEnable OBJECT-TYPE
                     SYNTAX  INTEGER {
                        useStatic(0),
                        useDhcp(1),
                        tryDhcpThenTryStatic(2),
                        notApplicable(255)
                     }
                     ACCESS  read-write
                     STATUS  mandatory
                     DESCRIPTION
                     "IP config method on the component network interface to modify
                     mode to static IP, DHCP and 'try DHCP then try static'.
                     If this network interface doesn't support DHCP, show
                     'notApplicable(255)'."
                     ::= { componentIPv4ConfigEntry 11 }

         componentIPv4ConfigMACAddr OBJECT-TYPE
                     SYNTAX  OCTET STRING
                     ACCESS  read-only
                     STATUS  deprecated
                     DESCRIPTION
                     "This is deprecated in favour of componentMACAddress from the componentMACAddressTable table"
                     ::= { componentIPv4ConfigEntry 12 }

        -- *************************************************************************
        -- componentIPv4ConfigTableCacheTimeout
        -- *************************************************************************
        componentIPv4ConfigTableCacheTimeout OBJECT-TYPE
                     SYNTAX  INTEGER
                     ACCESS  read-only
                     STATUS  mandatory
                     DESCRIPTION
                     "The timeout value (in seconds) of the cached data for the
                     table, componentIPv4ConfigTable.
                     This value is static (constant) and cannot be set."
                     ::= { componentNetworkConfiguration 2 }

         -- ********************************************************************************
         -- componentIPv6Config
         -- ********************************************************************************
         componentIPv6Config  OBJECT IDENTIFIER ::= { componentNetworkConfiguration 11 }

           componentIPv6ConfigTable OBJECT-TYPE
                      SYNTAX  SEQUENCE OF ComponentIPv6ConfigEntry
                      ACCESS  not-accessible
                      STATUS  mandatory
                      DESCRIPTION
                      "A table of IPv6 configuration options for components.

                      NOTE: This MIB object is not applicable to components that
                      do not support IPv6."
                      ::= { componentIPv6Config 1 }

           componentIPv6ConfigEntry  OBJECT-TYPE
                         SYNTAX ComponentIPv6ConfigEntry
                         ACCESS  not-accessible
                         STATUS  mandatory
                         DESCRIPTION
                         "IPv6 configuration options for a component.

                         NOTE: This MIB object is not applicable to components that
                         do not support IPv6."
                         INDEX { componentIPv6ConfigTopologyPath, componentIPv6ConfigPortIndex }
                         ::= { componentIPv6ConfigTable 1 }

           ComponentIPv6ConfigEntry ::= SEQUENCE {
                       componentIPv6ConfigTopologyPath  OCTET STRING,
                       componentIPv6ConfigPortIndex  INTEGER,
                       componentIPv6ConfigName  OCTET STRING,
                       componentIPv6ConfigEnabled  INTEGER,
                       componentIPv6ConfigStatic  INTEGER,
                       componentDHCPv6ConfigEnabled  INTEGER,
                       componentIPv6ConfigStatelessEnabled  INTEGER
                       }

           componentIPv6ConfigTopologyPath  OBJECT-TYPE
                       SYNTAX  OCTET STRING  (SIZE (0..100))
                       ACCESS  read-only
                       STATUS  mandatory
                       DESCRIPTION
                       "The unique identifier for a component in this table. The chassis and each
                        installed component is represented by a hardware topology tree, where
                        each node in the tree represents a component. The path to a particular
                        component consists of one or more <component>,<instance> pairs, where
                        each successive pair is a child of the previous parent pair.

                        As an example, the root of the tree is the chassis and is represented
                        by the pair 'CHASSIS, 1'. This pair indicates the first instance of
                        the chassis. If a blade is inserted in slot 4 of the chassis, its
                        topology path is 'CHASSIS, 1, BLADE, 4'. With this format, the
                        components in the chassis can be determined along with their relative
                        hierarchy to each other.

                        Note that this TP is preceded by a single octet that specifies the TP length.
                        This is required since this table is indexed with two indices and, therefore,
                        the TP length must be explicitly provided.

                        This component table is indexed by this unique topology
                        path and the numeric designations for the components are:

                         CHASSIS,                0x01   Chassis
                         MM,                     0x02   Management Module
                         BLADE,                  0x03   Main system board of a blade
                         POWER,                  0x04   Power Supply, Power Module, etc
                         COOLING,                0x05   Fan, blower, or other cooling device
                         IO_MODULE,              0x06   Has I/O interface, i.e. - switch or bridge
                         MEDIA,                  0x07   Media device
                         PROCESSOR,              0x08   Any processor, processor module, etc
                         STORAGE,                0x09   Any type of storage device
                         EXPANSION,              0x0A   Expansion Card (not covered by more specific type)
                         MEMORY,                 0x0B   Any memory device, module, etc
                         MFRU,                   0x0C   Managed FRU Device
                         PANEL,                  0x0D   Any sort of panel device, such as a front panel
                         BLADE_EXPANSION_MODULE, 0x0E   Expansion option (BEM) such as PEU, BSE, etc
                         CARD_EXPANSION,         0x0F   Expansion card, ie. daughter card
                         CARD_HS_EXPANSION,      0x10   High Speed Expansion card, ie. daughter card
                         INTERPOSER,             0x11   Interposer device
                         CLOCK,                  0x12   Clock card
                         MUX,                    0x13   Mulitplexer card
                         ADDIN,                  0x14   cKVM card & other addin cards
                         STORAGE_MODULE,         0x15   Container of one or more Storage Devices
                         SYS_EXPANSION_CARD,     0x16   Management card
                         BATTERY,                0x17   A single battery
                         BATTERY_MODULE,         0x18   Container of one or more batteries
                         REAR_LED,               0x19   Rear LED card
                         MEMORY_BANK,            0x1A   Memory banks
                         AIR_FILTER,             0x1B   Filter mechanism (bezel)
                         SERIAL_PORT_MODULE,     0x1C   Container of one or more serial ports
                         PARENT,                 0x1D   Reference to parent for multi-parent support
                         PHY_PORT,               0x1E   Physical port
                         IO_EXPANDER,            0x1F   RAID card
                         CABLE,                  0x20   Cable/Interconnect
                         FAN_MUX                 0x29   Fan multiplexer card
                     PCI_EXPRESS,            0x32   PCI express card on (PEN)
                     FLASH_DIMM,             0x33   Used for SPD devices that matches the silkscreen of the DIMM slot
                     RACK,                   0x50   Rack
                     PLATFORM,               0x51   Generic Platform like rack mounted server/appliance
                     DATAPLEX,               0x52   DataPlex
                     OTHER,                  0x53   Other unknown etc.
                     PERIPHERAL_MODULE,      0x54 
                     SYSTEM_BOARD,           0x55   System board
                     PROCESSOR_MODULE,       0x56 
                     BACK_PANEL,             0x57 
                     POWER_SYSTEM_BOARD,     0x58 
                     STORAGE_BACKPLANE,      0x59   Drive back plane
                     PROC_BOARD,             0x5A   Holds 1 or more processors
                     POWER_DI,               0x5B   Power mgt / power distribution board
                     CHASSIS_BACK_PANEL,     0x5C 
                     SUB_CHASSIS,            0x5D 
                     OTHER_CHASSIS_BOARD,    0x5E 
                     DEVICE_MODULE,          0x5F 
                     REMOTE_DEVICE,          0x60   Remote mgt communication device
                     EXTERNAL_ENVIRONMENT,   0x61   Such as external temp sensor for outside box temps
                     PROC_MEMORY_MODULE,     0x62   Processors and memory on same module"
                       ::= { componentIPv6ConfigEntry 1 }

           componentIPv6ConfigPortIndex OBJECT-TYPE
                       SYNTAX  INTEGER
                       ACCESS  read-only
                       STATUS  mandatory
                       DESCRIPTION
                       "The physical port number of the given entry"
                       ::= { componentIPv6ConfigEntry 2 }

           componentIPv6ConfigName OBJECT-TYPE
                       SYNTAX  OCTET STRING
                       ACCESS  read-only
                       STATUS  mandatory
                       DESCRIPTION
                       "The name of the component as a null terminated string."
                       ::= { componentIPv6ConfigEntry 3 }

           componentIPv6ConfigEnabled OBJECT-TYPE
                       SYNTAX  INTEGER { disable(0),enable(1) }
                       ACCESS  read-write
                       STATUS  mandatory
                       DESCRIPTION
                       "Enables/Disables IPv6 support on the component."
                       ::= { componentIPv6ConfigEntry 4 }

           componentIPv6ConfigStatic OBJECT-TYPE
                       SYNTAX  INTEGER { disable(0),enable(1) }
                       ACCESS  read-write
                       STATUS  mandatory
                       DESCRIPTION
                       "Enables/Disables IPv6 static configuration support on the component."
                       ::= { componentIPv6ConfigEntry 5 }

           componentDHCPv6ConfigEnabled OBJECT-TYPE
                       SYNTAX  INTEGER { disable(0),enable(1) }
                       ACCESS  read-write
                       STATUS  mandatory
                       DESCRIPTION
                       "Enables/Disables DHCPv6 address configuration support on the component."
                       ::= { componentIPv6ConfigEntry 6 }

           componentIPv6ConfigStatelessEnabled OBJECT-TYPE
                       SYNTAX  INTEGER { disable(0),enable(1) }
                       ACCESS  read-write
                       STATUS  mandatory
                       DESCRIPTION
                       "Enables/Disables IPv6 stateless auto-configuration support on the component."
                       ::= { componentIPv6ConfigEntry 7 }

        -- *************************************************************************
        -- componentIPv6ConfigTableCacheTimeout
        -- *************************************************************************
        componentIPv6ConfigTableCacheTimeout OBJECT-TYPE
                     SYNTAX  INTEGER
                     ACCESS  read-only
                     STATUS  mandatory
                     DESCRIPTION
                     "The timeout value (in seconds) of the cached data for the
                     table, componentIPv6ConfigTable.
                     This value is static (constant) and cannot be set."
                     ::= { componentIPv6Config 2 }

        componentIPv6AddressTable OBJECT-TYPE
                      SYNTAX  SEQUENCE OF ComponentIPv6AddressEntry
                      ACCESS  not-accessible
                      STATUS  mandatory
                      DESCRIPTION
                      "A table of assigned IPv6 addresses for components.

                      NOTE: This MIB object is not applicable to components that
                      do not support IPv6."
                      ::= { componentIPv6Config 6 }

           componentIPv6AddressEntry  OBJECT-TYPE
                       SYNTAX ComponentIPv6AddressEntry
                       ACCESS  not-accessible
                       STATUS  mandatory
                       DESCRIPTION
                       "The assigned IPv6 address for a given component.

                       NOTE: This MIB object is not applicable to components that
                       do not support IPv6."
                       INDEX { componentIPv6AddressTopologyPath, componentIPv6AddressPortIndex, componentIPv6AddressEntryIndex}
                       ::= { componentIPv6AddressTable 1 }

           ComponentIPv6AddressEntry ::= SEQUENCE {
                       componentIPv6AddressTopologyPath  OCTET STRING,
                       componentIPv6AddressPortIndex  INTEGER,
                       componentIPv6AddressEntryIndex  INTEGER,
                       componentIPv6AddressName  OCTET STRING,
                       componentIPv6AddressType  INTEGER,
                       componentIPv6Address  InetAddressIPv6,
                       componentIPv6AddressPrefixLen  INTEGER,
                       componentIPv6AddressDefaultRoute  InetAddressIPv6
                       }

           componentIPv6AddressTopologyPath  OBJECT-TYPE
                       SYNTAX  OCTET STRING  (SIZE (0..100))
                       ACCESS  read-only
                       STATUS  mandatory
                       DESCRIPTION
                       "The unique identifier for a component in this table. The chassis and each
                        installed component is represented by a hardware topology tree, where
                        each node in the tree represents a component. The path to a particular
                        component consists of one or more <component>,<instance> pairs, where
                        each successive pair is a child of the previous parent pair.

                        As an example, the root of the tree is the chassis and is represented
                        by the pair 'CHASSIS, 1'. This pair indicates the first instance of
                        the chassis. If a blade is inserted in slot 4 of the chassis, its
                        topology path is 'CHASSIS, 1, BLADE, 4'. With this format, the
                        components in the chassis can be determined along with their relative
                        hierarchy to each other.

                        Note that this TP is preceded by a single octet that specifies the TP length.
                        This is required since this table is indexed with multiple indices and, therefore,
                        the TP length must be explicitly provided.

                        This component table is indexed by this unique topology
                        path and the numeric designations for the components are:

                         CHASSIS,                0x01   Chassis
                         MM,                     0x02   Management Module
                         BLADE,                  0x03   Main system board of a blade
                         POWER,                  0x04   Power Supply, Power Module, etc
                         COOLING,                0x05   Fan, blower, or other cooling device
                         IO_MODULE,              0x06   Has I/O interface, i.e. - switch or bridge
                         MEDIA,                  0x07   Media device
                         PROCESSOR,              0x08   Any processor, processor module, etc
                         STORAGE,                0x09   Any type of storage device
                         EXPANSION,              0x0A   Expansion Card (not covered by more specific type)
                         MEMORY,                 0x0B   Any memory device, module, etc
                         MFRU,                   0x0C   Managed FRU Device
                         PANEL,                  0x0D   Any sort of panel device, such as a front panel
                         BLADE_EXPANSION_MODULE, 0x0E   Expansion option (BEM) such as PEU, BSE, etc
                         CARD_EXPANSION,         0x0F   Expansion card, ie. daughter card
                         CARD_HS_EXPANSION,      0x10   High Speed Expansion card, ie. daughter card
                         INTERPOSER,             0x11   Interposer device
                         CLOCK,                  0x12   Clock card
                         MUX,                    0x13   Mulitplexer card
                         ADDIN,                  0x14   cKVM card & other addin cards
                         STORAGE_MODULE,         0x15   Container of one or more Storage Devices
                         SYS_EXPANSION_CARD,     0x16   Management card
                         BATTERY,                0x17   A single battery
                         BATTERY_MODULE,         0x18   Container of one or more batteries
                         REAR_LED,               0x19   Rear LED card
                         MEMORY_BANK,            0x1A   Memory banks
                         AIR_FILTER,             0x1B   Filter mechanism (bezel)
                         SERIAL_PORT_MODULE,     0x1C   Container of one or more serial ports
                         PARENT,                 0x1D   Reference to parent for multi-parent support
                         PHY_PORT,               0x1E   Physical port
                         IO_EXPANDER,            0x1F   RAID card
                         CABLE,                  0x20   Cable/Interconnect
                         FAN_MUX                 0x29   Fan multiplexer card
                     PCI_EXPRESS,            0x32   PCI express card on (PEN)
                     FLASH_DIMM,             0x33   Used for SPD devices that matches the silkscreen of the DIMM slot
                     RACK,                   0x50   Rack
                     PLATFORM,               0x51   Generic Platform like rack mounted server/appliance
                     DATAPLEX,               0x52   DataPlex
                     OTHER,                  0x53   Other unknown etc.
                     PERIPHERAL_MODULE,      0x54 
                     SYSTEM_BOARD,           0x55   System board
                     PROCESSOR_MODULE,       0x56 
                     BACK_PANEL,             0x57 
                     POWER_SYSTEM_BOARD,     0x58 
                     STORAGE_BACKPLANE,      0x59   Drive back plane
                     PROC_BOARD,             0x5A   Holds 1 or more processors
                     POWER_DI,               0x5B   Power mgt / power distribution board
                     CHASSIS_BACK_PANEL,     0x5C 
                     SUB_CHASSIS,            0x5D 
                     OTHER_CHASSIS_BOARD,    0x5E 
                     DEVICE_MODULE,          0x5F 
                     REMOTE_DEVICE,          0x60   Remote mgt communication device
                     EXTERNAL_ENVIRONMENT,   0x61   Such as external temp sensor for outside box temps
                     PROC_MEMORY_MODULE,     0x62   Processors and memory on same module"
                       ::= { componentIPv6AddressEntry 1 }

           componentIPv6AddressPortIndex OBJECT-TYPE
                       SYNTAX  INTEGER
                       ACCESS  read-only
                       STATUS  mandatory
                       DESCRIPTION
                       "The component's physical port number for the given entry."
                       ::= { componentIPv6AddressEntry 2 }

           componentIPv6AddressEntryIndex OBJECT-TYPE
                       SYNTAX  INTEGER
                       ACCESS  read-only
                       STATUS  mandatory
                       DESCRIPTION
                       "The component's address entry index."
                       ::= { componentIPv6AddressEntry 3 }

           componentIPv6AddressName OBJECT-TYPE
                       SYNTAX  OCTET STRING
                       ACCESS  read-only
                       STATUS  mandatory
                       DESCRIPTION
                       "The name of the component as a null terminated string."
                       ::= { componentIPv6AddressEntry 4 }

           componentIPv6AddressType OBJECT-TYPE
                       SYNTAX  INTEGER
                       { active-static(1),
                         dhcp6(2),
                         link-local(3),
                         autconfig(4),
                         current(5) }
                       ACCESS  read-only
                       STATUS  mandatory
                       DESCRIPTION
                       "The address type."
                       ::= { componentIPv6AddressEntry 5 }

           componentIPv6Address OBJECT-TYPE
                     SYNTAX  InetAddressIPv6
                     ACCESS  read-write
                     STATUS  mandatory
                     DESCRIPTION
                     "The assigned IPv6 address.
                     Note: 'write' is for static ipv6 only."
                     ::= { componentIPv6AddressEntry 6 }

           componentIPv6AddressPrefixLen OBJECT-TYPE
                       SYNTAX  INTEGER (1..128)
                       ACCESS  read-write
                       STATUS  mandatory
                       DESCRIPTION
                       "The prefix length for the given address.
                       Note: 'write' is for static ipv6 only."
                       ::= { componentIPv6AddressEntry 7 }

           componentIPv6AddressDefaultRoute OBJECT-TYPE
                     SYNTAX  InetAddressIPv6
                     ACCESS  read-write
                     STATUS  mandatory
                     DESCRIPTION
                     "The default route used for the given address.
                     Note: 'write' is for static ipv6 only."
                     ::= { componentIPv6AddressEntry 8 }

        -- *************************************************************************
        -- componentIPv6AddressTableCacheTimeout
        -- *************************************************************************
        componentIPv6AddressTableCacheTimeout OBJECT-TYPE
                     SYNTAX  INTEGER
                     ACCESS  read-only
                     STATUS  mandatory
                     DESCRIPTION
                     "The timeout value (in seconds) of the cached data for the
                     table, componentIPv6AddressTable.
                     This value is static (constant) and cannot be set."
                     ::= { componentIPv6Config 7 }

      -- ********************************************************************************
      -- componentTimeTable
      -- ********************************************************************************
         componentTimeTable OBJECT-TYPE
                     SYNTAX  SEQUENCE OF ComponentTimeEntry
                     ACCESS  not-accessible
                     STATUS  mandatory
                     DESCRIPTION
                     "Table of Component NTP Configuration."
                     ::= { componentConfiguration 20 }

         componentTimeEntry OBJECT-TYPE
                    SYNTAX  ComponentTimeEntry
                    ACCESS  not-accessible
                    STATUS  mandatory
                    DESCRIPTION
                    "Component NTP Configuration entry."
                    INDEX { componentTimeTopologyPath }
                    ::= { componentTimeTable 1 }

         ComponentTimeEntry ::= SEQUENCE {
                  componentTimeTopologyPath OCTET STRING,
                  componentTimeName OCTET STRING,
                  componentTimeNTPEnable INTEGER,
                  componentTimeNTPFrequency INTEGER
                  }

         componentTimeTopologyPath  OBJECT-TYPE
                   SYNTAX  OCTET STRING  (SIZE (0..100))
                   ACCESS  read-only
                   STATUS  mandatory
                   DESCRIPTION
                   "The unique identifier for a component in this table. The chassis and each
                    installed component is represented by a hardware topology tree, where
                    each node in the tree represents a component. The path to a particular
                    component consists of one or more <component>,<instance> pairs, where
                    each successive pair is a child of the previous parent pair.

                    As an example, the root of the tree is the chassis and is represented
                    by the pair 'CHASSIS, 1'. This pair indicates the first instance of
                    the chassis. If a blade is inserted in slot 4 of the chassis, its
                    topology path is 'CHASSIS, 1, BLADE, 4'. With this format, the
                    components in the chassis can be determined along with their relative
                    hierarchy to each other.

                    This component table is indexed by this unique topology
                    path and the numeric designations for the components are:

                     CHASSIS,                0x01   Chassis
                     MM,                     0x02   Management Module
                     BLADE,                  0x03   Main system board of a blade
                     POWER,                  0x04   Power Supply, Power Module, etc
                     COOLING,                0x05   Fan, blower, or other cooling device
                     IO_MODULE,              0x06   Has I/O interface, i.e. - switch or bridge
                     MEDIA,                  0x07   Media device
                     PROCESSOR,              0x08   Any processor, processor module, etc
                     STORAGE,                0x09   Any type of storage device
                     EXPANSION,              0x0A   Expansion Card (not covered by more specific type)
                     MEMORY,                 0x0B   Any memory device, module, etc
                     MFRU,                   0x0C   Managed FRU Device
                     PANEL,                  0x0D   Any sort of panel device, such as a front panel
                     BLADE_EXPANSION_MODULE, 0x0E   Expansion option (BEM) such as PEU, BSE, etc
                     CARD_EXPANSION,         0x0F   Expansion card, ie. daughter card
                     CARD_HS_EXPANSION,      0x10   High Speed Expansion card, ie. daughter card
                     INTERPOSER,             0x11   Interposer device
                     CLOCK,                  0x12   Clock card
                     MUX,                    0x13   Mulitplexer card
                     ADDIN,                  0x14   cKVM card & other addin cards
                     STORAGE_MODULE,         0x15   Container of one or more Storage Devices
                     SYS_EXPANSION_CARD,     0x16   Management card
                     BATTERY,                0x17   A single battery
                     BATTERY_MODULE,         0x18   Container of one or more batteries
                     REAR_LED,               0x19   Rear LED card
                     MEMORY_BANK,            0x1A   Memory banks
                     AIR_FILTER,             0x1B   Filter mechanism (bezel)
                     SERIAL_PORT_MODULE,     0x1C   Container of one or more serial ports
                     PARENT,                 0x1D   Reference to parent for multi-parent support
                     PHY_PORT,               0x1E   Physical port
                     IO_EXPANDER,            0x1F   RAID card
                     CABLE,                  0x20   Cable/Interconnect
                     FAN_MUX                 0x29   Fan multiplexer card
                     PCI_EXPRESS,            0x32   PCI express card on (PEN)
                     FLASH_DIMM,             0x33   Used for SPD devices that matches the silkscreen of the DIMM slot
                     RACK,                   0x50   Rack
                     PLATFORM,               0x51   Generic Platform like rack mounted server/appliance
                     DATAPLEX,               0x52   DataPlex
                     OTHER,                  0x53   Other unknown etc.
                     PERIPHERAL_MODULE,      0x54 
                     SYSTEM_BOARD,           0x55   System board
                     PROCESSOR_MODULE,       0x56 
                     BACK_PANEL,             0x57 
                     POWER_SYSTEM_BOARD,     0x58 
                     STORAGE_BACKPLANE,      0x59   Drive back plane
                     PROC_BOARD,             0x5A   Holds 1 or more processors
                     POWER_DI,               0x5B   Power mgt / power distribution board
                     CHASSIS_BACK_PANEL,     0x5C 
                     SUB_CHASSIS,            0x5D 
                     OTHER_CHASSIS_BOARD,    0x5E 
                     DEVICE_MODULE,          0x5F 
                     REMOTE_DEVICE,          0x60   Remote mgt communication device
                     EXTERNAL_ENVIRONMENT,   0x61   Such as external temp sensor for outside box temps
                     PROC_MEMORY_MODULE,     0x62   Processors and memory on same module"
                   ::= { componentTimeEntry 1 }


         componentTimeName OBJECT-TYPE
                  SYNTAX  OCTET STRING
                  ACCESS  read-only
                  STATUS  mandatory
                  DESCRIPTION
                  "The name of the component as a null terminated string."
                  ::= { componentTimeEntry 2 }

         componentTimeNTPEnable OBJECT-TYPE
                  SYNTAX  INTEGER {
                    disabled(0),
                    enabled(1),
                    notApplicable(255)
                  }
                  ACCESS  read-write
                  STATUS  mandatory
                  DESCRIPTION
                  "This object allows the user to view the status of, and enable
                  or disable, a component's ability to have it's NTP information
                  updated by the CMM.

                  NOTE: If the component either does not exist or does not support
                  this feature, it displays 'notApplicable'."

                  ::= { componentTimeEntry 3 }

         componentTimeNTPFrequency OBJECT-TYPE
                  SYNTAX  INTEGER (0..44640)
                  ACCESS  read-write
                  STATUS  mandatory
                  DESCRIPTION
                  "This object allows the user to view or set the synchronization
                  frequency (in minutes) of the NTP information update from the CMM.

                  NOTE: If the component either does not exist or does not support
                  this feature, it displays '0'."

                  ::= { componentTimeEntry 4 }

      -- *************************************************************************
      -- componentTimeTableCacheTimeout
      -- *************************************************************************
         componentTimeTableCacheTimeout OBJECT-TYPE
                  SYNTAX  INTEGER
                  ACCESS  read-only
                  STATUS  mandatory
                  DESCRIPTION
                  "The timeout value (in seconds) of the cached data for the
                  table, componentTimeTable.
                  This value is static (constant) and cannot be set."
                  ::= { componentConfiguration 21 }

      -- ********************************************************************************
      -- componentSolTable
      -- ********************************************************************************
         componentSolTable OBJECT-TYPE
                   SYNTAX  SEQUENCE OF ComponentSolEntry
                   ACCESS  not-accessible
                   STATUS  mandatory
                   DESCRIPTION
                   "Component Serial-over-LAN (SOL) configuration table."
                   ::= { componentConfiguration 26 }

         componentSolEntry OBJECT-TYPE
                   SYNTAX  ComponentSolEntry
                   ACCESS  not-accessible
                   STATUS  mandatory
                   DESCRIPTION
                   "Component Serial-over-LAN (SOL) configuration entry."
                   INDEX { componentSolTopologyPath }
                   ::= { componentSolTable 1 }

         ComponentSolEntry ::= SEQUENCE {
                   componentSolTopologyPath OCTET STRING,
                   componentSolName OCTET STRING,
                   componentSolEnable INTEGER,
                   componentSolIpAddr  IpAddress,
                   componentSolSessionStatus  INTEGER,
                   componentSolCapability  INTEGER,
		   componentSolIpAddr6 InetAddressIPv6,
		   componentSolRetryInterval INTEGER,
		   componentSolRetryCount INTEGER,
		   componentSolBytesSent INTEGER,
		   componentSolBytesReceived INTEGER,
		   componentSolDestinationMAC OCTET STRING,
	           componentSolConsoleUserId OCTET STRING,
	           componentSolConsoleLoginFrom OCTET STRING,
		   componentSolConsoleLoginStart OCTET STRING,
		   componentSolConsoleLoginEnd OCTET STRING
                   }

         componentSolTopologyPath  OBJECT-TYPE
                   SYNTAX  OCTET STRING  (SIZE (0..100))
                   ACCESS  read-only
                   STATUS  mandatory
                   DESCRIPTION
                   "The unique identifier for a component in this table. The chassis and each
                    installed component is represented by a hardware topology tree, where
                    each node in the tree represents a component. The path to a particular
                    component consists of one or more <component>,<instance> pairs, where
                    each successive pair is a child of the previous parent pair.

                    As an example, the root of the tree is the chassis and is represented
                    by the pair 'CHASSIS, 1'. This pair indicates the first instance of
                    the chassis. If a blade is inserted in slot 4 of the chassis, its
                    topology path is 'CHASSIS, 1, BLADE, 4'. With this format, the
                    components in the chassis can be determined along with their relative
                    hierarchy to each other.

                    This component table is indexed by this unique topology
                    path and the numeric designations for the components are:

                     CHASSIS,                0x01   Chassis
                     MM,                     0x02   Management Module
                     BLADE,                  0x03   Main system board of a blade
                     POWER,                  0x04   Power Supply, Power Module, etc
                     COOLING,                0x05   Fan, blower, or other cooling device
                     IO_MODULE,              0x06   Has I/O interface, i.e. - switch or bridge
                     MEDIA,                  0x07   Media device
                     PROCESSOR,              0x08   Any processor, processor module, etc
                     STORAGE,                0x09   Any type of storage device
                     EXPANSION,              0x0A   Expansion Card (not covered by more specific type)
                     MEMORY,                 0x0B   Any memory device, module, etc
                     MFRU,                   0x0C   Managed FRU Device
                     PANEL,                  0x0D   Any sort of panel device, such as a front panel
                     BLADE_EXPANSION_MODULE, 0x0E   Expansion option (BEM) such as PEU, BSE, etc
                     CARD_EXPANSION,         0x0F   Expansion card, ie. daughter card
                     CARD_HS_EXPANSION,      0x10   High Speed Expansion card, ie. daughter card
                     INTERPOSER,             0x11   Interposer device
                     CLOCK,                  0x12   Clock card
                     MUX,                    0x13   Mulitplexer card
                     ADDIN,                  0x14   cKVM card & other addin cards
                     STORAGE_MODULE,         0x15   Container of one or more Storage Devices
                     SYS_EXPANSION_CARD,     0x16   Management card
                     BATTERY,                0x17   A single battery
                     BATTERY_MODULE,         0x18   Container of one or more batteries
                     REAR_LED,               0x19   Rear LED card
                     MEMORY_BANK,            0x1A   Memory banks
                     AIR_FILTER,             0x1B   Filter mechanism (bezel)
                     SERIAL_PORT_MODULE,     0x1C   Container of one or more serial ports
                     PARENT,                 0x1D   Reference to parent for multi-parent support
                     PHY_PORT,               0x1E   Physical port
                     IO_EXPANDER,            0x1F   RAID card
                     CABLE,                  0x20   Cable/Interconnect
                     FAN_MUX                 0x29   Fan multiplexer card
                     PCI_EXPRESS,            0x32   PCI express card on (PEN)
                     FLASH_DIMM,             0x33   Used for SPD devices that matches the silkscreen of the DIMM slot
                     RACK,                   0x50   Rack
                     PLATFORM,               0x51   Generic Platform like rack mounted server/appliance
                     DATAPLEX,               0x52   DataPlex
                     OTHER,                  0x53   Other unknown etc.
                     PERIPHERAL_MODULE,      0x54 
                     SYSTEM_BOARD,           0x55   System board
                     PROCESSOR_MODULE,       0x56 
                     BACK_PANEL,             0x57 
                     POWER_SYSTEM_BOARD,     0x58 
                     STORAGE_BACKPLANE,      0x59   Drive back plane
                     PROC_BOARD,             0x5A   Holds 1 or more processors
                     POWER_DI,               0x5B   Power mgt / power distribution board
                     CHASSIS_BACK_PANEL,     0x5C 
                     SUB_CHASSIS,            0x5D 
                     OTHER_CHASSIS_BOARD,    0x5E 
                     DEVICE_MODULE,          0x5F 
                     REMOTE_DEVICE,          0x60   Remote mgt communication device
                     EXTERNAL_ENVIRONMENT,   0x61   Such as external temp sensor for outside box temps
                     PROC_MEMORY_MODULE,     0x62   Processors and memory on same module"
                   ::= { componentSolEntry 1 }

         componentSolName OBJECT-TYPE
                    SYNTAX  OCTET STRING
                    ACCESS  read-only
                    STATUS  mandatory
                    DESCRIPTION
                    "The name of the component as a null terminated string."
                    ::= { componentSolEntry 2 }

         componentSolEnable  OBJECT-TYPE
                    SYNTAX  INTEGER {
                      solDisabled(0),
                      solEnabled(1)
                    }
                    ACCESS  read-write
                    STATUS  mandatory
                    DESCRIPTION
                    "Disable or enable the Serial-over-LAN (SOL) on a component."
                    ::= { componentSolEntry 3 }

         componentSolIpAddr   OBJECT-TYPE
                    SYNTAX  IpAddress
                    ACCESS  read-only
                    STATUS  deprecated
                    DESCRIPTION
                    " This is deprecated in favor of componentSolIpAddr.
		    IP address of the component derived from the IP address
                    range for the system management processors on the
                    component.

                    NOTE: The IPv6 address for a component can be view with the
                    componentIPv6AddressTable."
                    ::= { componentSolEntry 4 }

         componentSolSessionStatus OBJECT-TYPE
                    SYNTAX  INTEGER {
                      solSessionNotReady(0),
                      solSessionReady(1),
                      solSessionActive(2)
                    }
                    ACCESS  read-only
                    STATUS  mandatory
                    DESCRIPTION
                    "Status of a Serial-over-LAN (SOL) session:
                       solSessionNotReady: No SOL session connected to the
                                             component.
                       solSessionReady:    There is a SOL session to the
                                             component.
                       solSessionActive:   There is a SOL session to the
                                             component and there is a client
                                             using the SOL session."
                    ::= { componentSolEntry 5 }

         componentSolCapability OBJECT-TYPE
                    SYNTAX  INTEGER {
                      notSupport(0),
                      support(1)
                    }
                    ACCESS  read-only
                    STATUS  mandatory
                    DESCRIPTION
                    "Display whether or not the component supports the
                    Serial-over-LAN (SOL) feature."
                    ::= { componentSolEntry 6 }

	 componentSolIpAddr6 OBJECT-TYPE
                    SYNTAX InetAddressIPv6
                    ACCESS read-only
                    STATUS mandatory
                    DESCRIPTION
                    " IPv6 address of the blade."
                    ::= { componentSolEntry 7 }

         componentSolRetryInterval OBJECT-TYPE
                    SYNTAX INTEGER
                    ACCESS read-only
                    STATUS mandatory
                    DESCRIPTION
                    " Retry interval time in miliseconds."
                    ::={componentSolEntry 8}

         componentSolRetryCount OBJECT-TYPE
                    SYNTAX INTEGER
                    ACCESS read-only
                    STATUS mandatory
                    DESCRIPTION
                    " Retry count."
                    ::={componentSolEntry 9}

         componentSolBytesSent OBJECT-TYPE
                    SYNTAX INTEGER
                    ACCESS read-only
                    STATUS mandatory
                    DESCRIPTION
                    " Number of bytes sent."
                    ::={componentSolEntry 10}

         componentSolBytesReceived OBJECT-TYPE
                   SYNTAX INTEGER
                   ACCESS read-only
                   STATUS mandatory
                   DESCRIPTION
                   " Number of bytes received."
                   ::={componentSolEntry 11}

         componentSolDestinationMAC OBJECT-TYPE
                   SYNTAX OCTET STRING
                   ACCESS read-only
                   STATUS mandatory
                   DESCRIPTION
                   " MAC address of the blade."
                   ::={componentSolEntry 12}

         componentSolConsoleUserId OBJECT-TYPE
                   SYNTAX OCTET STRING
                   ACCESS read-only
                   STATUS mandatory
                   DESCRIPTION
                   " Sol console user name."
                   ::={componentSolEntry 13}

         componentSolConsoleLoginFrom OBJECT-TYPE
                   SYNTAX OCTET STRING
                   ACCESS read-only
                   STATUS mandatory
                   DESCRIPTION
                   " The location information from where the SOL console is logged in. "
                   ::={componentSolEntry 14}

         componentSolConsoleLoginStart OBJECT-TYPE
                   SYNTAX OCTET STRING
                   ACCESS read-only
                   STATUS mandatory
                   DESCRIPTION
                   " The time that SOL console starts. "
                   ::={componentSolEntry 15}

         componentSolConsoleLoginEnd OBJECT-TYPE
                   SYNTAX OCTET STRING
                   ACCESS read-only
		   STATUS mandatory
                   DESCRIPTION
                   " The time that SOL console ends. "
                   ::={componentSolEntry 16}

      -- *************************************************************************
      -- componentSolTableCacheTimeout
      -- *************************************************************************
         componentSolTableCacheTimeout OBJECT-TYPE
                  SYNTAX  INTEGER
                  ACCESS  read-only
                  STATUS  mandatory
                  DESCRIPTION
                  "The timeout value (in seconds) of the cached data for the
                  table, componentSolTable.
                  This value is static (constant) and cannot be set."
                  ::= { componentConfiguration 27 }

    -- ********************************************************************************
    -- componentMonitors
    -- ********************************************************************************
    componentMonitors OBJECT IDENTIFIER ::= { components 37 }

       -- ********************************************************************************
       -- componentSystemStatusTable
       -- ********************************************************************************

       componentSystemStatusTable OBJECT-TYPE
                     SYNTAX  SEQUENCE OF ComponentSystemStatusEntry
                     ACCESS  not-accessible
                     STATUS  mandatory
                     DESCRIPTION
                     "Table of component status information."
                     ::= { componentMonitors 1 }

       componentSystemStatusEntry OBJECT-TYPE
                     SYNTAX ComponentSystemStatusEntry
                     ACCESS  not-accessible
                     STATUS  mandatory
                     DESCRIPTION
                     "Component system status entry"
                     INDEX { componentStatusTopologyPath }
                     ::= { componentSystemStatusTable 1 }

       ComponentSystemStatusEntry ::= SEQUENCE {
                   componentStatusTopologyPath OCTET STRING,
                   componentStatusName OCTET STRING,
                   componentStatusPowerState INTEGER,
                   componentStatusHealthState INTEGER,
                   componentStatusPowerEnable INTEGER,
                   componentStatusWakeOnLanEnable INTEGER,
                   componentStatusWidth INTEGER,
                   componentStatusIOCompatibility OCTET STRING,
                   componentStatusInventoryReady INTEGER,
                   componentStatusBootCountPowerOnTimeBoots INTEGER,
                   componentStatusBootCountPowerOnTimeSecs INTEGER
                   }

        componentStatusTopologyPath  OBJECT-TYPE
                   SYNTAX  OCTET STRING  (SIZE (0..100))
                   ACCESS  read-only
                   STATUS  mandatory
                   DESCRIPTION
                   "The unique identifier for a component in this table. The chassis and each
                    installed component is represented by a hardware topology tree, where
                    each node in the tree represents a component. The path to a particular
                    component consists of one or more <component>,<instance> pairs, where
                    each successive pair is a child of the previous parent pair.

                    As an example, the root of the tree is the chassis and is represented
                    by the pair 'CHASSIS, 1'. This pair indicates the first instance of
                    the chassis. If a blade is inserted in slot 4 of the chassis, its
                    topology path is 'CHASSIS, 1, BLADE, 4'. With this format, the
                    components in the chassis can be determined along with their relative
                    hierarchy to each other.

                    This component table is indexed by this unique topology
                    path and the numeric designations for the components are:

                     CHASSIS,                0x01   Chassis
                     MM,                     0x02   Management Module
                     BLADE,                  0x03   Main system board of a blade
                     POWER,                  0x04   Power Supply, Power Module, etc
                     COOLING,                0x05   Fan, blower, or other cooling device
                     IO_MODULE,              0x06   Has I/O interface, i.e. - switch or bridge
                     MEDIA,                  0x07   Media device
                     PROCESSOR,              0x08   Any processor, processor module, etc
                     STORAGE,                0x09   Any type of storage device
                     EXPANSION,              0x0A   Expansion Card (not covered by more specific type)
                     MEMORY,                 0x0B   Any memory device, module, etc
                     MFRU,                   0x0C   Managed FRU Device
                     PANEL,                  0x0D   Any sort of panel device, such as a front panel
                     BLADE_EXPANSION_MODULE, 0x0E   Expansion option (BEM) such as PEU, BSE, etc
                     CARD_EXPANSION,         0x0F   Expansion card, ie. daughter card
                     CARD_HS_EXPANSION,      0x10   High Speed Expansion card, ie. daughter card
                     INTERPOSER,             0x11   Interposer device
                     CLOCK,                  0x12   Clock card
                     MUX,                    0x13   Mulitplexer card
                     ADDIN,                  0x14   cKVM card & other addin cards
                     STORAGE_MODULE,         0x15   Container of one or more Storage Devices
                     SYS_EXPANSION_CARD,     0x16   Management card
                     BATTERY,                0x17   A single battery
                     BATTERY_MODULE,         0x18   Container of one or more batteries
                     REAR_LED,               0x19   Rear LED card
                     MEMORY_BANK,            0x1A   Memory banks
                     AIR_FILTER,             0x1B   Filter mechanism (bezel)
                     SERIAL_PORT_MODULE,     0x1C   Container of one or more serial ports
                     PARENT,                 0x1D   Reference to parent for multi-parent support
                     PHY_PORT,               0x1E   Physical port
                     IO_EXPANDER,            0x1F   RAID card
                     CABLE,                  0x20   Cable/Interconnect
                     FAN_MUX                 0x29   Fan multiplexer card
                     PCI_EXPRESS,            0x32   PCI express card on (PEN)
                     FLASH_DIMM,             0x33   Used for SPD devices that matches the silkscreen of the DIMM slot
                     RACK,                   0x50   Rack
                     PLATFORM,               0x51   Generic Platform like rack mounted server/appliance
                     DATAPLEX,               0x52   DataPlex
                     OTHER,                  0x53   Other unknown etc.
                     PERIPHERAL_MODULE,      0x54 
                     SYSTEM_BOARD,           0x55   System board
                     PROCESSOR_MODULE,       0x56 
                     BACK_PANEL,             0x57 
                     POWER_SYSTEM_BOARD,     0x58 
                     STORAGE_BACKPLANE,      0x59   Drive back plane
                     PROC_BOARD,             0x5A   Holds 1 or more processors
                     POWER_DI,               0x5B   Power mgt / power distribution board
                     CHASSIS_BACK_PANEL,     0x5C 
                     SUB_CHASSIS,            0x5D 
                     OTHER_CHASSIS_BOARD,    0x5E 
                     DEVICE_MODULE,          0x5F 
                     REMOTE_DEVICE,          0x60   Remote mgt communication device
                     EXTERNAL_ENVIRONMENT,   0x61   Such as external temp sensor for outside box temps
                     PROC_MEMORY_MODULE,     0x62   Processors and memory on same module"
                   ::= { componentSystemStatusEntry 1 }

      componentStatusName OBJECT-TYPE
                   SYNTAX  OCTET STRING
                   ACCESS  read-only
                   STATUS  mandatory
                   DESCRIPTION
                   "The name of the component as a null terminated string."
                   ::= { componentSystemStatusEntry 2 }

      componentStatusPowerState  OBJECT-TYPE
                   SYNTAX  INTEGER {
                     off(0),
                     on(1),
                     standby(3),
                     hibernate(4)
                   }
                   ACCESS  read-only
                   STATUS  mandatory
                   DESCRIPTION
                   "Indicates the power state of the component specified."
                   ::= { componentSystemStatusEntry 3 }

       componentStatusHealthState  OBJECT-TYPE
                   SYNTAX  INTEGER {
                     unknown(0),
                     good(1),
                     warning(2),
                     critical(3),
                     kernelMode(4),
                     discovering(5),
                     commError(6),
                     noPower(7),
                     flashing(8),
                     initFailure(9),
                     insufficientPower(10),
                     powerDenied(11),
                     maintMode(12),
                     firehoseDump(13)
                   }
                   ACCESS  read-only
                   STATUS  mandatory
                   DESCRIPTION
                   "The system health state for the component.

                    Unknown: Component is in an undefined state.
                    Good: Component is operating normally.
                    Warning: One or more outstanding warnings exist for this component.
                    Critical: One or more outstanding critical events for this component.
                    Kernel Mode: Component is in kernel mode.
                    Discovering: The MM is currently in the process of discovering this component.
                    Communications Error: The MM failed to communicate with this component.
                    No Power: No power to the component's domain.
                    Flashing: Flashing in progress.
                    Initialization Failure: Component failed to initialized.
                    Insufficient Power: Not enough power is left in the component's domain to power the component.
                    Power Denied: Power was denied to the component."
                   ::= { componentSystemStatusEntry 4 }


       componentStatusPowerEnable  OBJECT-TYPE
                   SYNTAX  INTEGER {
                     disabled(0),
                     enabled(1)
                   }
                   ACCESS  read-only
                   STATUS  mandatory
                   DESCRIPTION
                   "Power enable state for the component."
                   ::= { componentSystemStatusEntry 5 }


       componentStatusWakeOnLanEnable  OBJECT-TYPE
                   SYNTAX  INTEGER {
                     disabled(0),
                     enabled(1),
                     notApplicable(255)
                   }
                   ACCESS  read-only
                   STATUS  mandatory
                   DESCRIPTION
                   "Wake on LAN enable state for the component."
                   ::= { componentSystemStatusEntry 6 }

      componentStatusWidth  OBJECT-TYPE
                   SYNTAX  INTEGER
                   ACCESS  read-only
                   STATUS  mandatory
                   DESCRIPTION
                   "The width of the component including any supplement component attached to it"
                   ::= { componentSystemStatusEntry 7 }

       componentStatusIOCompatibility OBJECT-TYPE
                   SYNTAX  OCTET STRING
                   ACCESS  read-only
                   STATUS  mandatory
                   DESCRIPTION
                   "I/O compatibility status for the blade. This reflects the 
                   worst-case status of this blades network adapter connections  
                   to all of the switches in the chassis. For example, if this 
                   blade has 4 network connections to the four IOMs in the chassis
                   and three are OK, but one indicates Attention, then this 
                   MIB object will indicate Attention. 

                   For an equivalent view using the web, visit the 
                   Chassis Management->Compute Nodes menu item and for a given 
                   blade, look at the I/O Compatibility column. Note that this column 
                   is not shown by default, but can be added to the view using the 
                   Columns dropdown to add it to the table.  

                   I/O compatibility status for the component.

                   The possible values and their meanings are as follows:

                   unknown: This indicates a communication error for the blade.

                   ok: This is the normal (good) case where the blade and the
                       corresponding I/O modules it is internally wired to have no
                       compatibility issues.

                   noIOMs: This means there are no I/O modules in any of the
                           corresponding I/O module bays this component is internally wired to.

                   attention: This indicates that one or more of the corresponding
                              I/O modules are in communication error.

                   mismatch: This indicates one of the following cases:
                             Fabric types are incompatible
                             An unknown I/O module type
                             An unknown fabric type on the component"
                   ::= { componentSystemStatusEntry 21 }

       componentStatusInventoryReady OBJECT-TYPE
                   SYNTAX  INTEGER {
                     notReady(0),
                     ready(1)
                   }
                   ACCESS  read-only
                   STATUS  mandatory
                   DESCRIPTION
                   "When a component management controller or the MM is reset, the
                    component inventory data is refreshed in the MM database. This includes
                    items like VPD (e.g. - serial number, UUID) and MAC address information.

                    Applications need to know when this information has been populated on the MM
                    before they begin to query it using SNMP or other means. This simple flag
                    object will return a ready or notReady indication for each component regarding the
                    status of this information.

                    Notes:

                    For components that are experiencing a 'communication failure' or
                    'initialization failure' condition, this object will continue to indicate
                    notReady until the condition is resolved. Therefore, any application that
                    polls this object should also incorporate a timeout period."
                   ::= { componentSystemStatusEntry 22 }

       componentStatusBootCountPowerOnTimeBoots  OBJECT-TYPE
                     SYNTAX  INTEGER
                     ACCESS  read-write
                     STATUS  mandatory
                     DESCRIPTION
                     "Blade boot count. This is valid for blade components and
                     otherwise is undefined. Writing this
                     value resets the boot count to zero."
                     ::= { componentSystemStatusEntry 23 }

         componentStatusBootCountPowerOnTimeSecs  OBJECT-TYPE
                     SYNTAX  INTEGER
                     ACCESS  read-write
                     STATUS  mandatory
                     DESCRIPTION
                     "Blade power on time in seconds. This is valid for blade
                     components and otherwise is undefined. Writing this
                     value resets the power on time to zero."
                     ::= { componentSystemStatusEntry 24 }

      -- *************************************************************************
      -- componentSystemStatusTableCacheTimeout
      -- *************************************************************************
         componentSystemStatusTableCacheTimeout OBJECT-TYPE
                  SYNTAX  INTEGER
                  ACCESS  read-only
                  STATUS  mandatory
                  DESCRIPTION
                  "The timeout value (in seconds) of the cached data for the
                  table, componentSystemStatusTable.
                  This value is static (constant) and cannot be set."
                  ::= { componentMonitors 2 }

      -- ********************************************************************************
      -- componentHealthSummaryTable
      -- ********************************************************************************
      componentHealthSummaryTable OBJECT-TYPE
                    SYNTAX  SEQUENCE OF ComponentHealthSummaryEntry
                    ACCESS  not-accessible
                    STATUS  mandatory
                    DESCRIPTION
                    "Table of component health summary information.
                    Contains information about the overall component health status.
                    Each component contains a list of critical or warning events for 
                    that component or severity of good or none if none exist.

                   NOTE: The table is not available on a telco chassis. See the 
                         telcoManagement branch of the MIB."
                    ::= { componentMonitors 6 }

      componentHealthSummaryEntry OBJECT-TYPE
                    SYNTAX ComponentHealthSummaryEntry
                    ACCESS  not-accessible
                    STATUS  mandatory
                    DESCRIPTION
                    "Component health summary entry"
                    INDEX { componentHealthTopologyPath, componentHealthEventIndex }
                    ::= { componentHealthSummaryTable 1 }

      ComponentHealthSummaryEntry ::= SEQUENCE {
                  componentHealthTopologyPath OCTET STRING,
                  componentHealthEventIndex INTEGER,
                  componentHealthSummaryName OCTET STRING,
                  componentHealthSummarySeverity OCTET STRING,
                  componentHealthSummaryDescription OCTET STRING,
                  componentHealthSummaryDateTime OCTET STRING,
                  componentHealthSummaryEventID OCTET STRING,
                  componentHealthSummaryCommonEventID OCTET STRING
                  }

      componentHealthTopologyPath  OBJECT-TYPE
                   SYNTAX  OCTET STRING  (SIZE (0..100))
                   ACCESS  read-only
                   STATUS  mandatory
                   DESCRIPTION
                   "The unique identifier for a component in this table. The chassis and each
                    installed component is represented by a hardware topology tree, where
                    each node in the tree represents a component. The path to a particular
                    component consists of one or more <component>,<instance> pairs, where
                    each successive pair is a child of the previous parent pair.

                    As an example, the root of the tree is the chassis and is represented
                    by the pair 'CHASSIS, 1'. This pair indicates the first instance of
                    the chassis. If a blade is inserted in slot 4 of the chassis, its
                    topology path is 'CHASSIS, 1, BLADE, 4'. With this format, the
                    components in the chassis can be determined along with their relative
                    hierarchy to each other.

                    Note that this TP is preceded by a single octet that specifies the TP length.
                    This is required since this table is indexed with two indices and, therefore,
                    the TP length must be explicitly provided.

                    This component table is indexed by this unique topology
                    path and the numeric designations for the components are:

                     CHASSIS,                0x01   Chassis
                     MM,                     0x02   Management Module
                     BLADE,                  0x03   Main system board of a blade
                     POWER,                  0x04   Power Supply, Power Module, etc
                     COOLING,                0x05   Fan, blower, or other cooling device
                     IO_MODULE,              0x06   Has I/O interface, i.e. - switch or bridge
                     MEDIA,                  0x07   Media device
                     PROCESSOR,              0x08   Any processor, processor module, etc
                     STORAGE,                0x09   Any type of storage device
                     EXPANSION,              0x0A   Expansion Card (not covered by more specific type)
                     MEMORY,                 0x0B   Any memory device, module, etc
                     MFRU,                   0x0C   Managed FRU Device
                     PANEL,                  0x0D   Any sort of panel device, such as a front panel
                     BLADE_EXPANSION_MODULE, 0x0E   Expansion option (BEM) such as PEU, BSE, etc
                     CARD_EXPANSION,         0x0F   Expansion card, ie. daughter card
                     CARD_HS_EXPANSION,      0x10   High Speed Expansion card, ie. daughter card
                     INTERPOSER,             0x11   Interposer device
                     CLOCK,                  0x12   Clock card
                     MUX,                    0x13   Mulitplexer card
                     ADDIN,                  0x14   cKVM card & other addin cards
                     STORAGE_MODULE,         0x15   Container of one or more Storage Devices
                     SYS_EXPANSION_CARD,     0x16   Management card
                     BATTERY,                0x17   A single battery
                     BATTERY_MODULE,         0x18   Container of one or more batteries
                     REAR_LED,               0x19   Rear LED card
                     MEMORY_BANK,            0x1A   Memory banks
                     AIR_FILTER,             0x1B   Filter mechanism (bezel)
                     SERIAL_PORT_MODULE,     0x1C   Container of one or more serial ports
                     PARENT,                 0x1D   Reference to parent for multi-parent support
                     PHY_PORT,               0x1E   Physical port
                     IO_EXPANDER,            0x1F   RAID card
                     CABLE,                  0x20   Cable/Interconnect
                     FAN_MUX                 0x29   Fan multiplexer card
                     PCI_EXPRESS,            0x32   PCI express card on (PEN)
                     FLASH_DIMM,             0x33   Used for SPD devices that matches the silkscreen of the DIMM slot
                     RACK,                   0x50   Rack
                     PLATFORM,               0x51   Generic Platform like rack mounted server/appliance
                     DATAPLEX,               0x52   DataPlex
                     OTHER,                  0x53   Other unknown etc.
                     PERIPHERAL_MODULE,      0x54 
                     SYSTEM_BOARD,           0x55   System board
                     PROCESSOR_MODULE,       0x56 
                     BACK_PANEL,             0x57 
                     POWER_SYSTEM_BOARD,     0x58 
                     STORAGE_BACKPLANE,      0x59   Drive back plane
                     PROC_BOARD,             0x5A   Holds 1 or more processors
                     POWER_DI,               0x5B   Power mgt / power distribution board
                     CHASSIS_BACK_PANEL,     0x5C 
                     SUB_CHASSIS,            0x5D 
                     OTHER_CHASSIS_BOARD,    0x5E 
                     DEVICE_MODULE,          0x5F 
                     REMOTE_DEVICE,          0x60   Remote mgt communication device
                     EXTERNAL_ENVIRONMENT,   0x61   Such as external temp sensor for outside box temps
                     PROC_MEMORY_MODULE,     0x62   Processors and memory on same module"
                   ::= { componentHealthSummaryEntry 1 }

       componentHealthEventIndex   OBJECT-TYPE
                   SYNTAX  INTEGER(0..255)
                   ACCESS  read-only
                   STATUS  mandatory
                   DESCRIPTION
                   "An index for the critical or warning health events for a given component."
                   ::= { componentHealthSummaryEntry 2 }

       componentHealthSummaryName OBJECT-TYPE
                   SYNTAX  OCTET STRING
                   ACCESS  read-only
                   STATUS  mandatory
                   DESCRIPTION
                   "The name of the component as a null terminated string."
                   ::= { componentHealthSummaryEntry 3 }

       componentHealthSummarySeverity  OBJECT-TYPE
                  SYNTAX  OCTET STRING
                  ACCESS  read-only
                  STATUS  mandatory
                  DESCRIPTION
                  "System health summary severity of an event for the given component."
                  ::= { componentHealthSummaryEntry 4 }

       componentHealthSummaryDescription  OBJECT-TYPE
                  SYNTAX  OCTET STRING
                  ACCESS  read-only
                  STATUS  mandatory
                  DESCRIPTION
                  "System health summary description of an event for the given component."
                  ::= { componentHealthSummaryEntry 5 }

       componentHealthSummaryDateTime  OBJECT-TYPE
                  SYNTAX  OCTET STRING
                  ACCESS  read-only
                  STATUS  mandatory
                  DESCRIPTION
                  "System health summary date time of an event for the given component."
                  ::= { componentHealthSummaryEntry 6 }

       componentHealthSummaryEventID  OBJECT-TYPE
                  SYNTAX  OCTET STRING
                  ACCESS  read-only
                  STATUS  mandatory
                  DESCRIPTION
                  "System health summary event ID of an event for the given component."
                  ::= { componentHealthSummaryEntry 7 }

      componentHealthSummaryCommonEventID  OBJECT-TYPE
                  SYNTAX  OCTET STRING
                  ACCESS  read-only
                  STATUS  mandatory
                  DESCRIPTION
                  "System health summary Common Event ID of an event for the given component."
                  ::= { componentHealthSummaryEntry 8 }

      -- *************************************************************************
      -- componentHealthSummaryTableCacheTimeout
      -- *************************************************************************
      componentHealthSummaryTableCacheTimeout OBJECT-TYPE
               SYNTAX  INTEGER
               ACCESS  read-only
               STATUS  mandatory
               DESCRIPTION
               "The timeout value (in seconds) of the cached data for the
               table, componentHealthSummaryTable.
               This value is static (constant) and cannot be set."
               ::= { componentMonitors 7 }

      -- ********************************************************************************
      -- componentMACAddressTable
      -- ********************************************************************************
      componentMACAddressTable OBJECT-TYPE
                     SYNTAX  SEQUENCE OF ComponentMACAddressEntry
                     ACCESS  not-accessible
                     STATUS  mandatory
                     DESCRIPTION
                     "Table of MAC address VPD information for each component."
                     ::= { componentMonitors 11 }

       componentMACAddressEntry OBJECT-TYPE
                     SYNTAX  ComponentMACAddressEntry
                     ACCESS  not-accessible
                     STATUS  mandatory
                     DESCRIPTION
                     "Component MAC address table entry"
                     INDEX { componentMACAddressTopologyPath, componentMACAddressIndex }
                     ::= { componentMACAddressTable 1 }

       ComponentMACAddressEntry ::= SEQUENCE {
                   componentMACAddressTopologyPath OCTET STRING,
                   componentMACAddressIndex INTEGER,
                   componentMACAddressName OCTET STRING,
                   componentMACAddress OCTET STRING
                   }

       componentMACAddressTopologyPath  OBJECT-TYPE
                   SYNTAX  OCTET STRING  (SIZE (0..100))
                   ACCESS  read-only
                   STATUS  mandatory
                   DESCRIPTION
                   "The unique identifier for a component in this table. The chassis and each
                    installed component is represented by a hardware topology tree, where
                    each node in the tree represents a component. The path to a particular
                    component consists of one or more <component>,<instance> pairs, where
                    each successive pair is a child of the previous parent pair.

                    As an example, the root of the tree is the chassis and is represented
                    by the pair 'CHASSIS, 1'. This pair indicates the first instance of
                    the chassis. If a blade is inserted in slot 4 of the chassis, its
                    topology path is 'CHASSIS, 1, BLADE, 4'. With this format, the
                    components in the chassis can be determined along with their relative
                    hierarchy to each other.

                    Note that this TP is preceded by a single octet that specifies the TP length.
                    This is required since this table is indexed with two indices and, therefore,
                    the TP length must be explicitly provided.

                    This component table is indexed by this unique topology
                    path and the numeric designations for the components are:

                     CHASSIS,                0x01   Chassis
                     MM,                     0x02   Management Module
                     BLADE,                  0x03   Main system board of a blade
                     POWER,                  0x04   Power Supply, Power Module, etc
                     COOLING,                0x05   Fan, blower, or other cooling device
                     IO_MODULE,              0x06   Has I/O interface, i.e. - switch or bridge
                     MEDIA,                  0x07   Media device
                     PROCESSOR,              0x08   Any processor, processor module, etc
                     STORAGE,                0x09   Any type of storage device
                     EXPANSION,              0x0A   Expansion Card (not covered by more specific type)
                     MEMORY,                 0x0B   Any memory device, module, etc
                     MFRU,                   0x0C   Managed FRU Device
                     PANEL,                  0x0D   Any sort of panel device, such as a front panel
                     BLADE_EXPANSION_MODULE, 0x0E   Expansion option (BEM) such as PEU, BSE, etc
                     CARD_EXPANSION,         0x0F   Expansion card, ie. daughter card
                     CARD_HS_EXPANSION,      0x10   High Speed Expansion card, ie. daughter card
                     INTERPOSER,             0x11   Interposer device
                     CLOCK,                  0x12   Clock card
                     MUX,                    0x13   Mulitplexer card
                     ADDIN,                  0x14   cKVM card & other addin cards
                     STORAGE_MODULE,         0x15   Container of one or more Storage Devices
                     SYS_EXPANSION_CARD,     0x16   Management card
                     BATTERY,                0x17   A single battery
                     BATTERY_MODULE,         0x18   Container of one or more batteries
                     REAR_LED,               0x19   Rear LED card
                     MEMORY_BANK,            0x1A   Memory banks
                     AIR_FILTER,             0x1B   Filter mechanism (bezel)
                     SERIAL_PORT_MODULE,     0x1C   Container of one or more serial ports
                     PARENT,                 0x1D   Reference to parent for multi-parent support
                     PHY_PORT,               0x1E   Physical port
                     IO_EXPANDER,            0x1F   RAID card
                     CABLE,                  0x20   Cable/Interconnect
                     FAN_MUX                 0x29   Fan multiplexer card
                     PCI_EXPRESS,            0x32   PCI express card on (PEN)
                     FLASH_DIMM,             0x33   Used for SPD devices that matches the silkscreen of the DIMM slot
                     RACK,                   0x50   Rack
                     PLATFORM,               0x51   Generic Platform like rack mounted server/appliance
                     DATAPLEX,               0x52   DataPlex
                     OTHER,                  0x53   Other unknown etc.
                     PERIPHERAL_MODULE,      0x54 
                     SYSTEM_BOARD,           0x55   System board
                     PROCESSOR_MODULE,       0x56 
                     BACK_PANEL,             0x57 
                     POWER_SYSTEM_BOARD,     0x58 
                     STORAGE_BACKPLANE,      0x59   Drive back plane
                     PROC_BOARD,             0x5A   Holds 1 or more processors
                     POWER_DI,               0x5B   Power mgt / power distribution board
                     CHASSIS_BACK_PANEL,     0x5C 
                     SUB_CHASSIS,            0x5D 
                     OTHER_CHASSIS_BOARD,    0x5E 
                     DEVICE_MODULE,          0x5F 
                     REMOTE_DEVICE,          0x60   Remote mgt communication device
                     EXTERNAL_ENVIRONMENT,   0x61   Such as external temp sensor for outside box temps
                     PROC_MEMORY_MODULE,     0x62   Processors and memory on same module"
                   ::= { componentMACAddressEntry 1 }

       componentMACAddressIndex  OBJECT-TYPE
                   SYNTAX  INTEGER
                   ACCESS  read-only
                   STATUS  mandatory
                   DESCRIPTION
                   "Each component may have one or more MAC address VPD values
                   associated with it, and this index object identifies the
                   particular instance."
                   ::= { componentMACAddressEntry 2 }

       componentMACAddressName OBJECT-TYPE
                   SYNTAX  OCTET STRING
                   ACCESS  read-only
                   STATUS  mandatory
                   DESCRIPTION
                   "The name of the component as a null terminated string."
                   ::= { componentMACAddressEntry 3 }

       componentMACAddress OBJECT-TYPE
                   SYNTAX  OCTET STRING
                   ACCESS  read-only
                   STATUS  mandatory
                   DESCRIPTION
                   "The MAC address VPD value for this component and index. The
                   value is a null terminated string.

                   For IOMs which are members of a stack, this field is not applicable and should be disregarded."
                   ::= { componentMACAddressEntry 4 }

      -- *************************************************************************
      -- componentMACAddressTableCacheTimeout
      -- *************************************************************************
      componentMACAddressTableCacheTimeout OBJECT-TYPE
               SYNTAX  INTEGER
               ACCESS  read-only
               STATUS  mandatory
               DESCRIPTION
               "The timeout value (in seconds) of the cached data for the
               table, componentMACAddressTable.
               This value is static (constant) and cannot be set."
               ::= { componentMonitors 12 }

      -- ********************************************************************************
      -- componentUniqueIDsTable
      -- ********************************************************************************
      componentUniqueIDsTable OBJECT-TYPE
                     SYNTAX  SEQUENCE OF ComponentUniqueIDsEntry
                     ACCESS  not-accessible
                     STATUS  mandatory
                     DESCRIPTION
                     "Table of unique ID information for each component."
                     ::= { componentMonitors 13 }

       componentUniqueIDsEntry OBJECT-TYPE
                     SYNTAX  ComponentUniqueIDsEntry
                     ACCESS  not-accessible
                     STATUS  mandatory
                     DESCRIPTION
                     "Component unique ID table entry"
                     INDEX { componentUniqueIDsTopologyPath, componentUniqueIDsIndex }
                     ::= { componentUniqueIDsTable 1 }

       ComponentUniqueIDsEntry ::= SEQUENCE {
                   componentUniqueIDsTopologyPath OCTET STRING,
                   componentUniqueIDsIndex INTEGER,
                   componentUniqueIDsName OCTET STRING,
                   componentUniqueIDsType INTEGER,
                   componentUniqueIDsValue OCTET STRING
                   }

       componentUniqueIDsTopologyPath  OBJECT-TYPE
                   SYNTAX  OCTET STRING  (SIZE (0..100))
                   ACCESS  read-only
                   STATUS  mandatory
                   DESCRIPTION
                   "The unique identifier for a component in this table. The chassis and each
                    installed component is represented by a hardware topology tree, where
                    each node in the tree represents a component. The path to a particular
                    component consists of one or more <component>,<instance> pairs, where
                    each successive pair is a child of the previous parent pair.

                    As an example, the root of the tree is the chassis and is represented
                    by the pair 'CHASSIS, 1'. This pair indicates the first instance of
                    the chassis. If a blade is inserted in slot 4 of the chassis, its
                    topology path is 'CHASSIS, 1, BLADE, 4'. With this format, the
                    components in the chassis can be determined along with their relative
                    hierarchy to each other.

                    Note that this TP is preceded by a single octet that specifies the TP length.
                    This is required since this table is indexed with two indices and, therefore,
                    the TP length must be explicitly provided.

                    This component table is indexed by this unique topology
                    path and the numeric designations for the components are:

                     CHASSIS,                0x01   Chassis
                     MM,                     0x02   Management Module
                     BLADE,                  0x03   Main system board of a blade
                     POWER,                  0x04   Power Supply, Power Module, etc
                     COOLING,                0x05   Fan, blower, or other cooling device
                     IO_MODULE,              0x06   Has I/O interface, i.e. - switch or bridge
                     MEDIA,                  0x07   Media device
                     PROCESSOR,              0x08   Any processor, processor module, etc
                     STORAGE,                0x09   Any type of storage device
                     EXPANSION,              0x0A   Expansion Card (not covered by more specific type)
                     MEMORY,                 0x0B   Any memory device, module, etc
                     MFRU,                   0x0C   Managed FRU Device
                     PANEL,                  0x0D   Any sort of panel device, such as a front panel
                     BLADE_EXPANSION_MODULE, 0x0E   Expansion option (BEM) such as PEU, BSE, etc
                     CARD_EXPANSION,         0x0F   Expansion card, ie. daughter card
                     CARD_HS_EXPANSION,      0x10   High Speed Expansion card, ie. daughter card
                     INTERPOSER,             0x11   Interposer device
                     CLOCK,                  0x12   Clock card
                     MUX,                    0x13   Mulitplexer card
                     ADDIN,                  0x14   cKVM card & other addin cards
                     STORAGE_MODULE,         0x15   Container of one or more Storage Devices
                     SYS_EXPANSION_CARD,     0x16   Management card
                     BATTERY,                0x17   A single battery
                     BATTERY_MODULE,         0x18   Container of one or more batteries
                     REAR_LED,               0x19   Rear LED card
                     MEMORY_BANK,            0x1A   Memory banks
                     AIR_FILTER,             0x1B   Filter mechanism (bezel)
                     SERIAL_PORT_MODULE,     0x1C   Container of one or more serial ports
                     PARENT,                 0x1D   Reference to parent for multi-parent support
                     PHY_PORT,               0x1E   Physical port
                     IO_EXPANDER,            0x1F   RAID card
                     CABLE,                  0x20   Cable/Interconnect
                     FAN_MUX                 0x29   Fan multiplexer card
                     PCI_EXPRESS,            0x32   PCI express card on (PEN)
                     FLASH_DIMM,             0x33   Used for SPD devices that matches the silkscreen of the DIMM slot
                     RACK,                   0x50   Rack
                     PLATFORM,               0x51   Generic Platform like rack mounted server/appliance
                     DATAPLEX,               0x52   DataPlex
                     OTHER,                  0x53   Other unknown etc.
                     PERIPHERAL_MODULE,      0x54 
                     SYSTEM_BOARD,           0x55   System board
                     PROCESSOR_MODULE,       0x56 
                     BACK_PANEL,             0x57 
                     POWER_SYSTEM_BOARD,     0x58 
                     STORAGE_BACKPLANE,      0x59   Drive back plane
                     PROC_BOARD,             0x5A   Holds 1 or more processors
                     POWER_DI,               0x5B   Power mgt / power distribution board
                     CHASSIS_BACK_PANEL,     0x5C 
                     SUB_CHASSIS,            0x5D 
                     OTHER_CHASSIS_BOARD,    0x5E 
                     DEVICE_MODULE,          0x5F 
                     REMOTE_DEVICE,          0x60   Remote mgt communication device
                     EXTERNAL_ENVIRONMENT,   0x61   Such as external temp sensor for outside box temps
                     PROC_MEMORY_MODULE,     0x62   Processors and memory on same module"
                   ::= { componentUniqueIDsEntry 1 }

       componentUniqueIDsIndex  OBJECT-TYPE
                   SYNTAX  INTEGER
                   ACCESS  read-only
                   STATUS  mandatory
                   DESCRIPTION
                   "Each component may have one or more unique ID values
                   associated with it, and this index object identifies the
                   particular instance."
                   ::= { componentUniqueIDsEntry 2 }

       componentUniqueIDsName OBJECT-TYPE
                   SYNTAX  OCTET STRING
                   ACCESS  read-only
                   STATUS  mandatory
                   DESCRIPTION
                   "The name of the component as a null terminated string."
                   ::= { componentUniqueIDsEntry 3 }

       componentUniqueIDsType OBJECT-TYPE
                   SYNTAX  INTEGER {
                      wwn(1),
                      guid(2),
                      sas(3)
                   }
                   ACCESS  read-only
                   STATUS  mandatory
                   DESCRIPTION
                   "Type of the unique ID in the object,
                   componentUniqueIDsValue. The type is one of the following:
                   World Wide Name (wwn), Global Unique IDs (guid) or
                   Serial Attach SCSI IDs (sas)."
                   ::= { componentUniqueIDsEntry 4 }

       componentUniqueIDsValue OBJECT-TYPE
                   SYNTAX  OCTET STRING (SIZE (0..255))
                   ACCESS  read-only
                   STATUS  mandatory
                   DESCRIPTION
                   "The unique ID value for this component and index. The
                   value is a null terminated string."
                   ::= { componentUniqueIDsEntry 5 }

      -- *************************************************************************
      -- componentUniqueIDsTableCacheTimeout
      -- *************************************************************************
      componentUniqueIDsTableCacheTimeout OBJECT-TYPE
               SYNTAX  INTEGER
               ACCESS  read-only
               STATUS  mandatory
               DESCRIPTION
               "The timeout value (in seconds) of the cached data for the
               table, componentUniqueIDsTable.
               This value is static (constant) and cannot be set."
               ::= { componentMonitors 14 }

      -- ********************************************************************************
      -- componentVoltagesTable
      -- ********************************************************************************
      componentVoltagesTable OBJECT-TYPE
                    SYNTAX  SEQUENCE OF ComponentVoltagesEntry
                    ACCESS  not-accessible
                    STATUS  mandatory
                    DESCRIPTION
                    "Table of component voltage sensor information."
                    ::= { componentMonitors 16 }

      componentVoltagesEntry OBJECT-TYPE
                    SYNTAX ComponentVoltagesEntry
                    ACCESS  not-accessible
                    STATUS  mandatory
                    DESCRIPTION "Component voltages entry."
                    INDEX { componentVoltagesTopologyPath, componentVoltagesSensorIndex }
                    ::= { componentVoltagesTable 1 }

      ComponentVoltagesEntry ::= SEQUENCE {
                  componentVoltagesTopologyPath OCTET STRING,
                  componentVoltagesSensorIndex INTEGER,
                  componentVoltagesComponentName OCTET STRING,
                  componentVoltagesSensorLabel OCTET STRING,
                  componentVoltagesSensorValue OCTET STRING,
                  componentVoltagesLowWarningThreshold OCTET STRING,
                  componentVoltagesHighWarningThreshold OCTET STRING
                  }

      componentVoltagesTopologyPath  OBJECT-TYPE
                   SYNTAX  OCTET STRING  (SIZE (0..100))
                   ACCESS  read-only
                   STATUS  mandatory
                   DESCRIPTION
                   "The unique identifier for a component in this table. The chassis and each
                    installed component is represented by a hardware topology tree, where
                    each node in the tree represents a component. The path to a particular
                    component consists of one or more <component>,<instance> pairs, where
                    each successive pair is a child of the previous parent pair.

                    As an example, the root of the tree is the chassis and is represented
                    by the pair 'CHASSIS, 1'. This pair indicates the first instance of
                    the chassis. If a blade is inserted in slot 4 of the chassis, its
                    topology path is 'CHASSIS, 1, BLADE, 4'. With this format, the
                    components in the chassis can be determined along with their relative
                    hierarchy to each other.

                    Note that this TP is preceded by a single octet that specifies the TP length.
                    This is required since this table is indexed with two indices and, therefore,
                    the TP length must be explicitly provided.

                    This component table is indexed by this unique topology
                    path and the numeric designations for the components are:

                     CHASSIS,                0x01   Chassis
                     MM,                     0x02   Management Module
                     BLADE,                  0x03   Main system board of a blade
                     POWER,                  0x04   Power Supply, Power Module, etc
                     COOLING,                0x05   Fan, blower, or other cooling device
                     IO_MODULE,              0x06   Has I/O interface, i.e. - switch or bridge
                     MEDIA,                  0x07   Media device
                     PROCESSOR,              0x08   Any processor, processor module, etc
                     STORAGE,                0x09   Any type of storage device
                     EXPANSION,              0x0A   Expansion Card (not covered by more specific type)
                     MEMORY,                 0x0B   Any memory device, module, etc
                     MFRU,                   0x0C   Managed FRU Device
                     PANEL,                  0x0D   Any sort of panel device, such as a front panel
                     BLADE_EXPANSION_MODULE, 0x0E   Expansion option (BEM) such as PEU, BSE, etc
                     CARD_EXPANSION,         0x0F   Expansion card, ie. daughter card
                     CARD_HS_EXPANSION,      0x10   High Speed Expansion card, ie. daughter card
                     INTERPOSER,             0x11   Interposer device
                     CLOCK,                  0x12   Clock card
                     MUX,                    0x13   Mulitplexer card
                     ADDIN,                  0x14   cKVM card & other addin cards
                     STORAGE_MODULE,         0x15   Container of one or more Storage Devices
                     SYS_EXPANSION_CARD,     0x16   Management card
                     BATTERY,                0x17   A single battery
                     BATTERY_MODULE,         0x18   Container of one or more batteries
                     REAR_LED,               0x19   Rear LED card
                     MEMORY_BANK,            0x1A   Memory banks
                     AIR_FILTER,             0x1B   Filter mechanism (bezel)
                     SERIAL_PORT_MODULE,     0x1C   Container of one or more serial ports
                     PARENT,                 0x1D   Reference to parent for multi-parent support
                     PHY_PORT,               0x1E   Physical port
                     IO_EXPANDER,            0x1F   RAID card
                     CABLE,                  0x20   Cable/Interconnect
                     FAN_MUX                 0x29   Fan multiplexer card
                     PCI_EXPRESS,            0x32   PCI express card on (PEN)
                     FLASH_DIMM,             0x33   Used for SPD devices that matches the silkscreen of the DIMM slot
                     RACK,                   0x50   Rack
                     PLATFORM,               0x51   Generic Platform like rack mounted server/appliance
                     DATAPLEX,               0x52   DataPlex
                     OTHER,                  0x53   Other unknown etc.
                     PERIPHERAL_MODULE,      0x54 
                     SYSTEM_BOARD,           0x55   System board
                     PROCESSOR_MODULE,       0x56 
                     BACK_PANEL,             0x57 
                     POWER_SYSTEM_BOARD,     0x58 
                     STORAGE_BACKPLANE,      0x59   Drive back plane
                     PROC_BOARD,             0x5A   Holds 1 or more processors
                     POWER_DI,               0x5B   Power mgt / power distribution board
                     CHASSIS_BACK_PANEL,     0x5C 
                     SUB_CHASSIS,            0x5D 
                     OTHER_CHASSIS_BOARD,    0x5E 
                     DEVICE_MODULE,          0x5F 
                     REMOTE_DEVICE,          0x60   Remote mgt communication device
                     EXTERNAL_ENVIRONMENT,   0x61   Such as external temp sensor for outside box temps
                     PROC_MEMORY_MODULE,     0x62   Processors and memory on same module"
                   ::= { componentVoltagesEntry 1 }

       componentVoltagesSensorIndex   OBJECT-TYPE
                   SYNTAX  INTEGER(0..255)
                   ACCESS  read-only
                   STATUS  mandatory
                   DESCRIPTION
                   "An index for the critical or warning health events for a given component."
                   ::= { componentVoltagesEntry 2 }

       componentVoltagesComponentName OBJECT-TYPE
                   SYNTAX  OCTET STRING
                   ACCESS  read-only
                   STATUS  mandatory
                   DESCRIPTION
                   "The name of the component as a null terminated string."
                   ::= { componentVoltagesEntry 3 }

       componentVoltagesSensorLabel OBJECT-TYPE
                   SYNTAX  OCTET STRING
                   ACCESS  read-only
                   STATUS  mandatory
                   DESCRIPTION
                   "The label of the sensor as a null terminated string."
                   ::= { componentVoltagesEntry 4 }

       componentVoltagesSensorValue OBJECT-TYPE
                   SYNTAX  OCTET STRING
                   ACCESS  read-only
                   STATUS  mandatory
                   DESCRIPTION
                   "The value of the sensor as a null terminated string."
                   ::= { componentVoltagesEntry 5 }

      componentVoltagesLowWarningThreshold OBJECT-TYPE
                   SYNTAX  OCTET STRING
                   ACCESS  read-only
                   STATUS  mandatory
                   DESCRIPTION
                   "The low warning threshold of the sensor as a null terminated string."
                   ::= { componentVoltagesEntry 6 }

      componentVoltagesHighWarningThreshold OBJECT-TYPE
                   SYNTAX  OCTET STRING
                   ACCESS  read-only
                   STATUS  mandatory
                   DESCRIPTION
                   "The high warning threshold of the sensor as a null terminated string."
                   ::= { componentVoltagesEntry 7 }

      -- *************************************************************************
      -- componentVoltagesTableCacheTimeout
      -- *************************************************************************
      componentVoltagesTableCacheTimeout OBJECT-TYPE
               SYNTAX  INTEGER
               ACCESS  read-only
               STATUS  mandatory
               DESCRIPTION
               "The timeout value (in seconds) of the cached data for the
               table, componentVoltagesTable.
               This value is static (constant) and cannot be set."
               ::= { componentMonitors 17 }

      -- ********************************************************************************
      -- componentTemperaturesTable
      -- ********************************************************************************
      componentTemperaturesTable OBJECT-TYPE
                    SYNTAX  SEQUENCE OF ComponentTemperaturesEntry
                    ACCESS  not-accessible
                    STATUS  mandatory
                    DESCRIPTION
                    "Table of component temperature sensor information."
                    ::= { componentMonitors 21 }

      componentTemperaturesEntry OBJECT-TYPE
                    SYNTAX ComponentTemperaturesEntry
                    ACCESS  not-accessible
                    STATUS  mandatory
                    DESCRIPTION "Component temperatures entry."
                    INDEX { componentTemperaturesTopologyPath, componentTemperaturesSensorIndex }
                    ::= { componentTemperaturesTable 1 }

      ComponentTemperaturesEntry ::= SEQUENCE {
                  componentTemperaturesTopologyPath OCTET STRING,
                  componentTemperaturesSensorIndex INTEGER,
                  componentTemperaturesComponentName OCTET STRING,
                  componentTemperaturesSensorLabel OCTET STRING,
                  componentTemperaturesSensorValue OCTET STRING,
                  componentTemperaturesWarningThreshold OCTET STRING,
                  componentTemperaturesShutdownThreshold OCTET STRING,
                  componentTemperaturesWarningResetThreshold OCTET STRING
                  }

      componentTemperaturesTopologyPath  OBJECT-TYPE
                   SYNTAX  OCTET STRING  (SIZE (0..100))
                   ACCESS  read-only
                   STATUS  mandatory
                   DESCRIPTION
                   "The unique identifier for a component in this table. The chassis and each
                    installed component is represented by a hardware topology tree, where
                    each node in the tree represents a component. The path to a particular
                    component consists of one or more <component>,<instance> pairs, where
                    each successive pair is a child of the previous parent pair.

                    As an example, the root of the tree is the chassis and is represented
                    by the pair 'CHASSIS, 1'. This pair indicates the first instance of
                    the chassis. If a blade is inserted in slot 4 of the chassis, its
                    topology path is 'CHASSIS, 1, BLADE, 4'. With this format, the
                    components in the chassis can be determined along with their relative
                    hierarchy to each other.

                    Note that this TP is preceded by a single octet that specifies the TP length.
                    This is required since this table is indexed with two indices and, therefore,
                    the TP length must be explicitly provided.

                    This component table is indexed by this unique topology
                    path and the numeric designations for the components are:

                     CHASSIS,                0x01   Chassis
                     MM,                     0x02   Management Module
                     BLADE,                  0x03   Main system board of a blade
                     POWER,                  0x04   Power Supply, Power Module, etc
                     COOLING,                0x05   Fan, blower, or other cooling device
                     IO_MODULE,              0x06   Has I/O interface, i.e. - switch or bridge
                     MEDIA,                  0x07   Media device
                     PROCESSOR,              0x08   Any processor, processor module, etc
                     STORAGE,                0x09   Any type of storage device
                     EXPANSION,              0x0A   Expansion Card (not covered by more specific type)
                     MEMORY,                 0x0B   Any memory device, module, etc
                     MFRU,                   0x0C   Managed FRU Device
                     PANEL,                  0x0D   Any sort of panel device, such as a front panel
                     BLADE_EXPANSION_MODULE, 0x0E   Expansion option (BEM) such as PEU, BSE, etc
                     CARD_EXPANSION,         0x0F   Expansion card, ie. daughter card
                     CARD_HS_EXPANSION,      0x10   High Speed Expansion card, ie. daughter card
                     INTERPOSER,             0x11   Interposer device
                     CLOCK,                  0x12   Clock card
                     MUX,                    0x13   Mulitplexer card
                     ADDIN,                  0x14   cKVM card & other addin cards
                     STORAGE_MODULE,         0x15   Container of one or more Storage Devices
                     SYS_EXPANSION_CARD,     0x16   Management card
                     BATTERY,                0x17   A single battery
                     BATTERY_MODULE,         0x18   Container of one or more batteries
                     REAR_LED,               0x19   Rear LED card
                     MEMORY_BANK,            0x1A   Memory banks
                     AIR_FILTER,             0x1B   Filter mechanism (bezel)
                     SERIAL_PORT_MODULE,     0x1C   Container of one or more serial ports
                     PARENT,                 0x1D   Reference to parent for multi-parent support
                     PHY_PORT,               0x1E   Physical port
                     IO_EXPANDER,            0x1F   RAID card
                     CABLE,                  0x20   Cable/Interconnect
                     FAN_MUX                 0x29   Fan multiplexer card
                     PCI_EXPRESS,            0x32   PCI express card on (PEN)
                     FLASH_DIMM,             0x33   Used for SPD devices that matches the silkscreen of the DIMM slot
                     RACK,                   0x50   Rack
                     PLATFORM,               0x51   Generic Platform like rack mounted server/appliance
                     DATAPLEX,               0x52   DataPlex
                     OTHER,                  0x53   Other unknown etc.
                     PERIPHERAL_MODULE,      0x54 
                     SYSTEM_BOARD,           0x55   System board
                     PROCESSOR_MODULE,       0x56 
                     BACK_PANEL,             0x57 
                     POWER_SYSTEM_BOARD,     0x58 
                     STORAGE_BACKPLANE,      0x59   Drive back plane
                     PROC_BOARD,             0x5A   Holds 1 or more processors
                     POWER_DI,               0x5B   Power mgt / power distribution board
                     CHASSIS_BACK_PANEL,     0x5C 
                     SUB_CHASSIS,            0x5D 
                     OTHER_CHASSIS_BOARD,    0x5E 
                     DEVICE_MODULE,          0x5F 
                     REMOTE_DEVICE,          0x60   Remote mgt communication device
                     EXTERNAL_ENVIRONMENT,   0x61   Such as external temp sensor for outside box temps
                     PROC_MEMORY_MODULE,     0x62   Processors and memory on same module"
                   ::= { componentTemperaturesEntry 1 }

       componentTemperaturesSensorIndex   OBJECT-TYPE
                   SYNTAX  INTEGER(0..255)
                   ACCESS  read-only
                   STATUS  mandatory
                   DESCRIPTION
                   "An index for the temperature Sensors for a given component."
                   ::= { componentTemperaturesEntry 2 }

       componentTemperaturesComponentName OBJECT-TYPE
                   SYNTAX  OCTET STRING
                   ACCESS  read-only
                   STATUS  mandatory
                   DESCRIPTION
                   "The name of the component as a null terminated string."
                   ::= { componentTemperaturesEntry 3 }

       componentTemperaturesSensorLabel OBJECT-TYPE
                   SYNTAX  OCTET STRING
                   ACCESS  read-only
                   STATUS  mandatory
                   DESCRIPTION
                   "The label of the sensor as a null terminated string."
                   ::= { componentTemperaturesEntry 4 }

       componentTemperaturesSensorValue OBJECT-TYPE
                   SYNTAX  OCTET STRING
                   ACCESS  read-only
                   STATUS  mandatory
                   DESCRIPTION
                   "The value of the sensor as a null terminated string."
                   ::= { componentTemperaturesEntry 5 }

      componentTemperaturesWarningThreshold OBJECT-TYPE
                   SYNTAX  OCTET STRING
                   ACCESS  read-only
                   STATUS  mandatory
                   DESCRIPTION
                   "The warning threshold of the sensor as a null terminated string."
                   ::= { componentTemperaturesEntry 6 }

      componentTemperaturesShutdownThreshold OBJECT-TYPE
                   SYNTAX  OCTET STRING
                   ACCESS  read-only
                   STATUS  mandatory
                   DESCRIPTION
                   "The Shutdown threshold of the sensor as a null terminated string."
                   ::= { componentTemperaturesEntry 7 }

      componentTemperaturesWarningResetThreshold OBJECT-TYPE
                   SYNTAX  OCTET STRING
                   ACCESS  read-only
                   STATUS  mandatory
                   DESCRIPTION
                   "The Warning Reset threshold of the sensor as a null terminated string."
                   ::= { componentTemperaturesEntry 8 }

      -- *************************************************************************
      -- componentTemperaturesTableCacheTimeout
      -- *************************************************************************
      componentTemperaturesTableCacheTimeout OBJECT-TYPE
               SYNTAX  INTEGER
               ACCESS  read-only
               STATUS  mandatory
               DESCRIPTION
               "The timeout value (in seconds) of the cached data for the
               table, componentTemperaturesTable.
               This value is static (constant) and cannot be set."
               ::= { componentMonitors 22 }

                   
      -- ********************************************************************************
      -- componentIOCompatibilityTable
      -- ********************************************************************************
      componentIOCompatibilityTable OBJECT-TYPE
                    SYNTAX  SEQUENCE OF ComponentIOCompatibilityEntry
                    ACCESS  not-accessible
                    STATUS  mandatory
                    DESCRIPTION
                    "Table of component IO Compatibility information. This table 
                     has a row for each switch connection to each node."
                    ::= { componentMonitors 26 }

      componentIOCompatibilityEntry OBJECT-TYPE
                    SYNTAX ComponentIOCompatibilityEntry
                    ACCESS  not-accessible
                    STATUS  mandatory
                    DESCRIPTION "Component IO compatibility entry."
                    INDEX { componentIOCompatibilityTopologyPath, componentIOCompatibilityIOMBay }
                    ::= { componentIOCompatibilityTable 1 }

      ComponentIOCompatibilityEntry ::= SEQUENCE {
                  componentIOCompatibilityTopologyPath OCTET STRING,
                  componentIOCompatibilityIOMBay INTEGER,
                  componentIOCompatibilityComponentName OCTET STRING,
                  componentIOCompatibilityIOMPower OCTET STRING,
                  componentIOCompatibilityIOMFabricType OCTET STRING,
                  componentIOCompatibilityFabricOnComponent OCTET STRING,
                  componentIOCompatibilityStatus OCTET STRING
              }

      componentIOCompatibilityTopologyPath  OBJECT-TYPE
                   SYNTAX  OCTET STRING  (SIZE (0..100))
                   ACCESS  read-only
                   STATUS  mandatory
                   DESCRIPTION
                   "The topology path of the node.

                    The unique identifier for a component in this table. The chassis and each
                    installed component is represented by a hardware topology tree, where
                    each node in the tree represents a component. The path to a particular
                    component consists of one or more <component>,<instance> pairs, where
                    each successive pair is a child of the previous parent pair.

                    As an example, the root of the tree is the chassis and is represented
                    by the pair 'CHASSIS, 1'. This pair indicates the first instance of
                    the chassis. If a blade is inserted in slot 4 of the chassis, its
                    topology path is 'CHASSIS, 1, BLADE, 4'. With this format, the
                    components in the chassis can be determined along with their relative
                    hierarchy to each other.

                    Note that this TP is preceded by a single octet that specifies the TP length.
                    This is required since this table is indexed with two indices and, therefore,
                    the TP length must be explicitly provided.

                    This component table is indexed by this unique topology
                    path and the numeric designations for the components are:

                     CHASSIS,                0x01   Chassis
                     MM,                     0x02   Management Module
                     BLADE,                  0x03   Main system board of a blade
                     POWER,                  0x04   Power Supply, Power Module, etc
                     COOLING,                0x05   Fan, blower, or other cooling device
                     IO_MODULE,              0x06   Has I/O interface, i.e. - switch or bridge
                     MEDIA,                  0x07   Media device
                     PROCESSOR,              0x08   Any processor, processor module, etc
                     STORAGE,                0x09   Any type of storage device
                     EXPANSION,              0x0A   Expansion Card (not covered by more specific type)
                     MEMORY,                 0x0B   Any memory device, module, etc
                     MFRU,                   0x0C   Managed FRU Device
                     PANEL,                  0x0D   Any sort of panel device, such as a front panel
                     BLADE_EXPANSION_MODULE, 0x0E   Expansion option (BEM) such as PEU, BSE, etc
                     CARD_EXPANSION,         0x0F   Expansion card, ie. daughter card
                     CARD_HS_EXPANSION,      0x10   High Speed Expansion card, ie. daughter card
                     INTERPOSER,             0x11   Interposer device
                     CLOCK,                  0x12   Clock card
                     MUX,                    0x13   Mulitplexer card
                     ADDIN,                  0x14   cKVM card & other addin cards
                     STORAGE_MODULE,         0x15   Container of one or more Storage Devices
                     SYS_EXPANSION_CARD,     0x16   Management card
                     BATTERY,                0x17   A single battery
                     BATTERY_MODULE,         0x18   Container of one or more batteries
                     REAR_LED,               0x19   Rear LED card
                     MEMORY_BANK,            0x1A   Memory banks
                     AIR_FILTER,             0x1B   Filter mechanism (bezel)
                     SERIAL_PORT_MODULE,     0x1C   Container of one or more serial ports
                     PARENT,                 0x1D   Reference to parent for multi-parent support
                     PHY_PORT,               0x1E   Physical port
                     IO_EXPANDER,            0x1F   RAID card
                     CABLE,                  0x20   Cable/Interconnect
                     FAN_MUX                 0x29   Fan multiplexer card
                     PCI_EXPRESS,            0x32   PCI express card on (PEN)
                     FLASH_DIMM,             0x33   Used for SPD devices that matches the silkscreen of the DIMM slot
                     RACK,                   0x50   Rack
                     PLATFORM,               0x51   Generic Platform like rack mounted server/appliance
                     DATAPLEX,               0x52   DataPlex
                     OTHER,                  0x53   Other unknown etc.
                     PERIPHERAL_MODULE,      0x54 
                     SYSTEM_BOARD,           0x55   System board
                     PROCESSOR_MODULE,       0x56 
                     BACK_PANEL,             0x57 
                     POWER_SYSTEM_BOARD,     0x58 
                     STORAGE_BACKPLANE,      0x59   Drive back plane
                     PROC_BOARD,             0x5A   Holds 1 or more processors
                     POWER_DI,               0x5B   Power mgt / power distribution board
                     CHASSIS_BACK_PANEL,     0x5C 
                     SUB_CHASSIS,            0x5D 
                     OTHER_CHASSIS_BOARD,    0x5E 
                     DEVICE_MODULE,          0x5F 
                     REMOTE_DEVICE,          0x60   Remote mgt communication device
                     EXTERNAL_ENVIRONMENT,   0x61   Such as external temp sensor for outside box temps
                     PROC_MEMORY_MODULE,     0x62   Processors and memory on same module"
                   ::= { componentIOCompatibilityEntry 1 }
                   
       componentIOCompatibilityIOMBay   OBJECT-TYPE
                   SYNTAX  INTEGER(0..255)
                   ACCESS  read-only
                   STATUS  mandatory
                   DESCRIPTION
                   "The slot number of the switch that this node has an internal connection to."
                   ::= { componentIOCompatibilityEntry 2 }

       componentIOCompatibilityComponentName OBJECT-TYPE
                   SYNTAX  OCTET STRING
                   ACCESS  read-only
                   STATUS  mandatory
                   DESCRIPTION                                              
                   "The name of the node as a null terminated string."
                   ::= { componentIOCompatibilityEntry 3 }
                   
       componentIOCompatibilityIOMPower OBJECT-TYPE
                    SYNTAX  OCTET STRING
                    ACCESS  read-only
                    STATUS  mandatory
                    DESCRIPTION
                    "The power state of the IO module specified in componentIOCompatibilityIOMBay.
                    n/a if module not installed."
                    ::= { componentIOCompatibilityEntry 4 }

        componentIOCompatibilityIOMFabricType OBJECT-TYPE
                    SYNTAX  OCTET STRING
                    ACCESS  read-only
                    STATUS  mandatory
                    DESCRIPTION
                    "The fabric type of the IO module specified in componentIOCompatibilityIOMBay."
                    ::= { componentIOCompatibilityEntry 5 }

        componentIOCompatibilityFabricOnComponent OBJECT-TYPE
                    SYNTAX  OCTET STRING
                    ACCESS  read-only
                    STATUS  mandatory
                    DESCRIPTION
                    "The fabric type for this channel on the node (may be onboard fabric or
                    an expansion card)."
                    ::= { componentIOCompatibilityEntry 6 }

        componentIOCompatibilityStatus OBJECT-TYPE
                    SYNTAX  OCTET STRING
                    ACCESS  read-only
                    STATUS  mandatory
                    DESCRIPTION
                    "The compatibility status between the node network adapter port and the IO module specified
                    in componentIOCompatibilityIOMBay.

                    For an equivalent view using the web, visit the Chassis Management->Compute Nodes menu item
                    and for a given blade, click on the link under the Device Name column. From here, select the 
                    IO Conenctivity tab which will show a row for each switch module. The compatibility status
                    is shown for each switch. 

                    The possible values are:

                    OK: No compatibility issues

                    No IOM: There is no IO module on the other side of the wire for this channel on the blade.

                    n/a: (Not applicable) The IO module specified in componentIOCompatibilityIOMBay is a bridge,
                          so the component port cannot connect to it.

                    Attention: The IO module specified in componentIOCompatibilityIOMBay has a communication error.

                    Mismatch: Indicates one of the following cases:
                           Fabric types are incompatible
                           Module specified in componentIOCompatibilityIOMBay is of unknown type
                           Unknown fabric type on the component"
                    ::= { componentIOCompatibilityEntry 7 }

      -- *************************************************************************
      -- componentIOCompatibilityTableCacheTimeout
      -- *************************************************************************
      componentIOCompatibilityTableCacheTimeout OBJECT-TYPE
               SYNTAX  INTEGER
               ACCESS  read-only
               STATUS  mandatory
               DESCRIPTION
               "The timeout value (in seconds) of the cached data for the
               table, componentIOCompatibilityTable.
               This value is static (constant) and cannot be set."
               ::= { componentMonitors 27 }



      -- *************************************************************************
      -- Node Connectivity Information
      -- *************************************************************************

		nodeConnectivityTable OBJECT-TYPE
			SYNTAX SEQUENCE OF NodeConnectivityEntry
			ACCESS not-accessible
			STATUS mandatory
			DESCRIPTION
				"Table of node connectivity information. This table provides information
				 related to the node communication status."
			::= { componentMonitors 31}

		nodeConnectivityEntry OBJECT-TYPE
                  SYNTAX NodeConnectivityEntry
                  ACCESS  not-accessible
                  STATUS  mandatory
                  DESCRIPTION
                    "Connectivity information for nodes."
                  INDEX { nodeConnectivityIndex }
                  ::= { nodeConnectivityTable 1 }

		NodeConnectivityEntry ::= SEQUENCE {
					nodeConnectivityIndex             INTEGER,
					nodeConnectivityName              OCTET STRING,
					nodeConnectivityStatus            INTEGER
                  }

		nodeConnectivityIndex  OBJECT-TYPE
                   SYNTAX  INTEGER (0..128)
                   ACCESS  read-only
                   STATUS  mandatory
                   DESCRIPTION
                   "Node Connectivity table index.  "
                   ::= { nodeConnectivityEntry 1 }

		nodeConnectivityName OBJECT-TYPE
                   SYNTAX  OCTET STRING
                   ACCESS  read-only
                   STATUS  mandatory
                   DESCRIPTION
                   "The name of the node as a null terminated string."
                   ::= { nodeConnectivityEntry 2 }

		nodeConnectivityStatus  OBJECT-TYPE
                   SYNTAX  INTEGER {
                     notcommunicating(0),
                     communicating(1)
                   }
                   ACCESS  read-only
                   STATUS  mandatory
                   DESCRIPTION
                   "Indicates the communication status of the node."
                   ::= { nodeConnectivityEntry 3 }


      -- ********************************************************************************
      -- componentServiceResetTable
      -- ********************************************************************************
    componentServiceReset OBJECT IDENTIFIER ::= { components 38 }

    componentServiceResetTable OBJECT-TYPE
                     SYNTAX  SEQUENCE OF ComponentServiceResetEntry
                     ACCESS  not-accessible
                     STATUS  mandatory
                     DESCRIPTION
                     "A table providing aux power status and the ability
                      to perform a virtual reseat or hard restart of a component."
                     ::= { componentServiceReset 1 }

       componentServiceResetEntry OBJECT-TYPE
                     SYNTAX  ComponentServiceResetEntry
                     ACCESS  not-accessible
                     STATUS  mandatory
                     DESCRIPTION
                     "Component module power service reset entry"
                     INDEX { componentServiceResetTopologyPath }
                     ::= { componentServiceResetTable 1 }

       ComponentServiceResetEntry ::= SEQUENCE {
                   componentServiceResetTopologyPath OCTET STRING,
                   componentServiceResetName OCTET STRING,
                   componentServiceResetStatus INTEGER,
                   componentServiceResetCmd INTEGER
                   }

        componentServiceResetTopologyPath  OBJECT-TYPE
                  SYNTAX  OCTET STRING  (SIZE (0..100))
                  ACCESS  read-only
                  STATUS  mandatory
                  DESCRIPTION
                  "The unique identifier for a row in this table. The chassis and each
                   installed component is represented by a hardware topology tree, where
                   each node in the tree represents a component. The path to a particular
                   component consists of one or more <component>,<instance> pairs, where
                   each successive pair is a child of the previous parent pair.

                   As an example, the root of the tree is the chassis and is represented
                   by the pair 'CHASSIS, 1'. This pair indicates the first instance of
                   the chassis. If a blade is inserted in slot 4 of the chassis, its
                   topology path is 'CHASSIS, 1, BLADE, 4'. With this format, the
                   components in the chassis can be determined along with their relative
                   hierarchy to each other.

                   This component table is indexed by this unique topology
                   path and the numeric designations for the components are:

                    CHASSIS,                0x01   Chassis
                    MM,                     0x02   Management Module
                    BLADE,                  0x03   Main system board of a blade
                    POWER,                  0x04   Power Supply, Power Module, etc
                    COOLING,                0x05   Fan, blower, or other cooling device
                    IO_MODULE,              0x06   Has I/O interface, i.e. - switch or bridge
                    MEDIA,                  0x07   Media device
                    PROCESSOR,              0x08   Any processor, processor module, etc
                    STORAGE,                0x09   Any type of storage device
                    EXPANSION,              0x0A   Expansion Card (not covered by more specific type)
                    MEMORY,                 0x0B   Any memory device, module, etc
                    MFRU,                   0x0C   Managed FRU Device
                    PANEL,                  0x0D   Any sort of panel device, such as a front panel
                    BLADE_EXPANSION_MODULE, 0x0E   Expansion option (BEM) such as PEU, BSE, etc
                    CARD_EXPANSION,         0x0F   Expansion card, ie. daughter card
                    CARD_HS_EXPANSION,      0x10   High Speed Expansion card, ie. daughter card
                    INTERPOSER,             0x11   Interposer device
                    CLOCK,                  0x12   Clock card
                    MUX,                    0x13   Mulitplexer card
                    ADDIN,                  0x14   cKVM card & other addin cards
                    STORAGE_MODULE,         0x15   Container of one or more Storage Devices
                    SYS_EXPANSION_CARD,     0x16   Management card
                    BATTERY,                0x17   A single battery
                    BATTERY_MODULE,         0x18   Container of one or more batteries
                    MEDIA_MODULE,           0x19   Container of one or more media devices
                    MEMORY_BANK,            0x1A   Memory banks
                    AIR_FILTER,             0x1B   Filter mechanism (bezel)
                    SERIAL_PORT_MODULE,     0x1C   Container of one or more serial ports
                    PARENT,                 0x1D   Reference to parent for multi-parent support
                    PHY_PORT,               0x1E   Physical port
                    IO_EXPANDER,            0x1F   RAID card
                    CABLE,                  0x20   Cable/Interconnect
                    FAN_MUX,                0x29   Fan multiplexer card
                     PCI_EXPRESS,            0x32   PCI express card on (PEN)
                     FLASH_DIMM,             0x33   Used for SPD devices that matches the silkscreen of the DIMM slot
                     RACK,                   0x50   Rack
                     PLATFORM,               0x51   Generic Platform like rack mounted server/appliance
                     DATAPLEX,               0x52   DataPlex
                     OTHER,                  0x53   Other unknown etc.
                     PERIPHERAL_MODULE,      0x54 
                     SYSTEM_BOARD,           0x55   System board
                     PROCESSOR_MODULE,       0x56 
                     BACK_PANEL,             0x57 
                     POWER_SYSTEM_BOARD,     0x58 
                     STORAGE_BACKPLANE,      0x59   Drive back plane
                     PROC_BOARD,             0x5A   Holds 1 or more processors
                     POWER_DI,               0x5B   Power mgt / power distribution board
                     CHASSIS_BACK_PANEL,     0x5C 
                     SUB_CHASSIS,            0x5D 
                     OTHER_CHASSIS_BOARD,    0x5E 
                     DEVICE_MODULE,          0x5F 
                     REMOTE_DEVICE,          0x60   Remote mgt communication device
                     EXTERNAL_ENVIRONMENT,   0x61   Such as external temp sensor for outside box temps
                     PROC_MEMORY_MODULE,     0x62   Processors and memory on same module"

                  ::= { componentServiceResetEntry 1 }

      componentServiceResetName  OBJECT-TYPE
                  SYNTAX  OCTET STRING
                  ACCESS  read-only
                  STATUS  mandatory
                  DESCRIPTION
                  "A short text string describing the particular component. For the
                   MM and blades, this name will be the configured name or its
                   serial number if no user configured name is available. For all
                   other components, this object will provide text to identify the
                   component."
                  ::= { componentServiceResetEntry 2 }

       componentServiceResetStatus   OBJECT-TYPE
                   SYNTAX  INTEGER {
                       auxPowerOff(0),
                       auxPowerOn(1),
                       unknown(255)
                     }
                   ACCESS  read-only
                   STATUS  mandatory
                   DESCRIPTION
                   "Status of the aux power.  A value of auxPowerOff(0) indicates
                   that the componant aux power is off.  A value of
                   auxPowerOn(1) indicates that the componant aux power is on."
                   ::= { componentServiceResetEntry 3 }

       componentServiceResetCmd   OBJECT-TYPE
                   SYNTAX  INTEGER {
                       noOperation(0),
                       resetVirtualReseatOperation(1),
                       resetHardRestartOperation(2)
                     }
                   ACCESS  read-write
                   STATUS  mandatory
                   DESCRIPTION
		           "NOTE: Do not perform this service reset operation on a node that is
                   currently in a maintenance mode state. See componentStatusHealthState in
                   componentSystemStatusTable for maintMode(12) value.


                   To reset the auxiliary power on a component, set this object to
                   resetVirtualReseatOperation(1). This will toggle the auxiliary 
                   power and simulate a physical removal and insertion.
                   During the operation, auxiliary power is removed from the component 
                   and is then restored. For nodes, the power state will remain off and the 
                   user will need to manually power on the node.  

                   To perform a hard restart on the component, set this object to 
                   resetHardRestartOperation(2). This will toggle the reset line to the 
                   processor causing it to re-initialize. 

                   This object is intended to be write-only.

                   The component will experience a temporary loss of communication and the power 
                   state will change. Prior to executing this action, perform any operations needed
                   to protect user data.

                   Reading this object will always return the value of noOperation(0)."
                   ::= { componentServiceResetEntry 4 }

      -- *************************************************************************
      -- componentServiceResetTableCacheTimeout
      -- *************************************************************************
      componentServiceResetTableCacheTimeout OBJECT-TYPE
               SYNTAX  INTEGER
               ACCESS  read-only
               STATUS  mandatory
               DESCRIPTION
               "The timeout value (in seconds) of the cached data for the
               table, componentServiceResetTable.
               This value is static (constant) and cannot be set."
               ::= { componentServiceReset 2 }

 componentLEDs OBJECT IDENTIFIER ::= { components 39 }

      -- ********************************************************************************
      -- componentLEDsTable
      -- ********************************************************************************
      componentLEDsTable OBJECT-TYPE
                    SYNTAX  SEQUENCE OF ComponentLEDsEntry
                    ACCESS  not-accessible
                    STATUS  mandatory
                    DESCRIPTION
                    "Table of component LED information.

                     NOTE: Querying objects in this table may take significantly longer
                     than normal, so it is recommended that the query timeout be set to
                     a large value. On a fully populated chassis, the timeout should be set
                     to 120 seconds or more."
                    ::= { componentLEDs 1 }

       componentLEDsEntry OBJECT-TYPE
                     SYNTAX ComponentLEDsEntry
                     ACCESS  not-accessible
                     STATUS  mandatory
                     DESCRIPTION
                     "Component LEDs information entry"
                     INDEX { ledComponentTopologyPath }
                     ::= { componentLEDsTable 1 }

       ComponentLEDsEntry ::= SEQUENCE {
                   ledComponentTopologyPath OCTET STRING,
                   ledComponentName OCTET STRING,
                   ledComponentFault INTEGER,
                   ledComponentCheckLog INTEGER,
                   ledComponentIdentity INTEGER
                   }

       ledComponentTopologyPath  OBJECT-TYPE
                   SYNTAX  OCTET STRING  (SIZE (0..100))
                   ACCESS  read-only
                   STATUS  mandatory
                   DESCRIPTION
                   "The unique identifier for a component in this table. The chassis and each
                    installed component is represented by a hardware topology tree, where
                    each node in the tree represents a component. The path to a particular
                    component consists of one or more <component>,<instance> pairs, where
                    each successive pair is a child of the previous parent pair.

                    As an example, the root of the tree is the chassis and is represented
                    by the pair 'CHASSIS, 1'. This pair indicates the first instance of
                    the chassis. If a blade is inserted in slot 4 of the chassis, its
                    topology path is 'CHASSIS, 1, BLADE, 4'. With this format, the
                    components in the chassis can be determined along with their relative
                    hierarchy to each other.

                    This component table is indexed by this unique topology
                    path and the numeric designations for the components are:

                     CHASSIS,                0x01   Chassis
                     MM,                     0x02   Management Module
                     BLADE,                  0x03   Main system board of a blade
                     POWER,                  0x04   Power Supply, Power Module, etc
                     COOLING,                0x05   Fan, blower, or other cooling device
                     IO_MODULE,              0x06   Has I/O interface, i.e. - switch or bridge
                     MEDIA,                  0x07   Media device
                     PROCESSOR,              0x08   Any processor, processor module, etc
                     STORAGE,                0x09   Any type of storage device
                     EXPANSION,              0x0A   Expansion Card (not covered by more specific type)
                     MEMORY,                 0x0B   Any memory device, module, etc
                     MFRU,                   0x0C   Managed FRU Device
                     PANEL,                  0x0D   Any sort of panel device, such as a front panel
                     BLADE_EXPANSION_MODULE, 0x0E   Expansion option (BEM) such as PEU, BSE, etc
                     CARD_EXPANSION,         0x0F   Expansion card, ie. daughter card
                     CARD_HS_EXPANSION,      0x10   High Speed Expansion card, ie. daughter card
                     INTERPOSER,             0x11   Interposer device
                     CLOCK,                  0x12   Clock card
                     MUX,                    0x13   Mulitplexer card
                     ADDIN,                  0x14   cKVM card & other addin cards
                     STORAGE_MODULE,         0x15   Container of one or more Storage Devices
                     SYS_EXPANSION_CARD,     0x16   Management card
                     BATTERY,                0x17   A single battery
                     BATTERY_MODULE,         0x18   Container of one or more batteries
                     REAR_LED,               0x19   Rear LED card
                     MEMORY_BANK,            0x1A   Memory banks
                     AIR_FILTER,             0x1B   Filter mechanism (bezel)
                     SERIAL_PORT_MODULE,     0x1C   Container of one or more serial ports
                     PARENT,                 0x1D   Reference to parent for multi-parent support
                     PHY_PORT,               0x1E   Physical port
                     IO_EXPANDER,            0x1F   RAID card
                     CABLE,                  0x20   Cable/Interconnect
                     FAN_MUX                 0x29   Fan multiplexer card
                     PCI_EXPRESS,            0x32   PCI express card on (PEN)
                     FLASH_DIMM,             0x33   Used for SPD devices that matches the silkscreen of the DIMM slot
                     RACK,                   0x50   Rack
                     PLATFORM,               0x51   Generic Platform like rack mounted server/appliance
                     DATAPLEX,               0x52   DataPlex
                     OTHER,                  0x53   Other unknown etc.
                     PERIPHERAL_MODULE,      0x54 
                     SYSTEM_BOARD,           0x55   System board
                     PROCESSOR_MODULE,       0x56 
                     BACK_PANEL,             0x57 
                     POWER_SYSTEM_BOARD,     0x58 
                     STORAGE_BACKPLANE,      0x59   Drive back plane
                     PROC_BOARD,             0x5A   Holds 1 or more processors
                     POWER_DI,               0x5B   Power mgt / power distribution board
                     CHASSIS_BACK_PANEL,     0x5C 
                     SUB_CHASSIS,            0x5D 
                     OTHER_CHASSIS_BOARD,    0x5E 
                     DEVICE_MODULE,          0x5F 
                     REMOTE_DEVICE,          0x60   Remote mgt communication device
                     EXTERNAL_ENVIRONMENT,   0x61   Such as external temp sensor for outside box temps
                     PROC_MEMORY_MODULE,     0x62   Processors and memory on same module"
                   ::= { componentLEDsEntry 1 }

       ledComponentName OBJECT-TYPE
                   SYNTAX  OCTET STRING
                   ACCESS  read-only
                   STATUS  mandatory
                   DESCRIPTION
                   "The name of the component as a null terminated string."
                   ::= { componentLEDsEntry 2 }

       ledComponentFault  OBJECT-TYPE
                   SYNTAX  INTEGER {
                     off(0),
                     on(1)
                   }
                   ACCESS  read-only
                   STATUS  mandatory
                   DESCRIPTION
                   "Indicates whether the component fault LED is on or off."
                   ::= { componentLEDsEntry 3 }

       ledComponentCheckLog  OBJECT-TYPE
                   SYNTAX  INTEGER {
                     off(0),
                     on(1)
                   }
                   ACCESS  read-write
                   STATUS  mandatory
                   DESCRIPTION
                   "Indicates whether the component check log information LED is on or off.
                   For Write access, the LED can be turned off only."
                   ::= { componentLEDsEntry 4 }

       ledComponentIdentity OBJECT-TYPE
                   SYNTAX  INTEGER {
                     off(0),
                     on(1),
                     blinking(2)
                   }
                   ACCESS  read-write
                   STATUS  mandatory
                   DESCRIPTION
                   "Indicates whether the component identify LED is on, off, or blinking."
                   ::= { componentLEDsEntry 5 }

      -- ********************************************************************************
      -- componentLEDsTableCacheTimeout
      -- ********************************************************************************
       componentLEDsTableCacheTimeout OBJECT-TYPE
                   SYNTAX  INTEGER
                   ACCESS  read-only
                   STATUS  mandatory
                   DESCRIPTION
                   "The timeout value (in seconds) of the cached data for the
                   table, componentLEDsTable.
                   This value is static (constant) and cannot be set."
                   ::= { componentLEDs 2 }

      -- ********************************************************************************
      -- componentLEDsDetailsTable
      -- ********************************************************************************
      componentLEDsDetailsTable OBJECT-TYPE
                     SYNTAX  SEQUENCE OF ComponentLEDsDetailsEntry
                     ACCESS  not-accessible
                     STATUS  mandatory
                     DESCRIPTION
                     "Table of LED info for each component."
                     ::= { componentLEDs 9 }

       componentLEDsDetailsEntry OBJECT-TYPE
                     SYNTAX  ComponentLEDsDetailsEntry
                     ACCESS  not-accessible
                     STATUS  mandatory
                     DESCRIPTION
                     "Component LED info table entry"
                     INDEX { componentLEDsDetailsTopologyPath, componentLEDsDetailsIndex }
                     ::= { componentLEDsDetailsTable 1 }

       ComponentLEDsDetailsEntry ::= SEQUENCE {
                   componentLEDsDetailsTopologyPath OCTET STRING,
                   componentLEDsDetailsIndex INTEGER,
                   componentLEDsDetailsComponentType OCTET STRING,
                   componentLEDsDetailsLabel OCTET STRING,
                   componentLEDsDetailsState INTEGER,
                   componentLEDsDetailsLocation OCTET STRING
                   }

       componentLEDsDetailsTopologyPath  OBJECT-TYPE
                   SYNTAX  OCTET STRING  (SIZE (0..100))
                   ACCESS  read-only
                   STATUS  mandatory
                   DESCRIPTION
                   "The unique identifier for a component in this table. The chassis and each
                    installed component is represented by a hardware topology tree, where
                    each node in the tree represents a component. The path to a particular
                    component consists of one or more <component>,<instance> pairs, where
                    each successive pair is a child of the previous parent pair.

                    As an example, the root of the tree is the chassis and is represented
                    by the pair 'CHASSIS, 1'. This pair indicates the first instance of
                    the chassis. If a blade is inserted in slot 4 of the chassis, its
                    topology path is 'CHASSIS, 1, BLADE, 4'. With this format, the
                    components in the chassis can be determined along with their relative
                    hierarchy to each other.

                    Note that this TP is preceded by a single octet that specifies the TP length.
                    This is required since this table is indexed with two indices and, therefore,
                    the TP length must be explicitly provided.

                    This component table is indexed by this unique topology
                    path and the numeric designations for the components are:

                     CHASSIS,                0x01   Chassis
                     MM,                     0x02   Management Module
                     BLADE,                  0x03   Main system board of a blade
                     POWER,                  0x04   Power Supply, Power Module, etc
                     COOLING,                0x05   Fan, blower, or other cooling device
                     IO_MODULE,              0x06   Has I/O interface, i.e. - switch or bridge
                     MEDIA,                  0x07   Media device
                     PROCESSOR,              0x08   Any processor, processor module, etc
                     STORAGE,                0x09   Any type of storage device
                     EXPANSION,              0x0A   Expansion Card (not covered by more specific type)
                     MEMORY,                 0x0B   Any memory device, module, etc
                     MFRU,                   0x0C   Managed FRU Device
                     PANEL,                  0x0D   Any sort of panel device, such as a front panel
                     BLADE_EXPANSION_MODULE, 0x0E   Expansion option (BEM) such as PEU, BSE, etc
                     CARD_EXPANSION,         0x0F   Expansion card, ie. daughter card
                     CARD_HS_EXPANSION,      0x10   High Speed Expansion card, ie. daughter card
                     INTERPOSER,             0x11   Interposer device
                     CLOCK,                  0x12   Clock card
                     MUX,                    0x13   Mulitplexer card
                     ADDIN,                  0x14   cKVM card & other addin cards
                     STORAGE_MODULE,         0x15   Container of one or more Storage Devices
                     SYS_EXPANSION_CARD,     0x16   Management card
                     BATTERY,                0x17   A single battery
                     BATTERY_MODULE,         0x18   Container of one or more batteries
                     REAR_LED,               0x19   Rear LED card
                     MEMORY_BANK,            0x1A   Memory banks
                     AIR_FILTER,             0x1B   Filter mechanism (bezel)
                     SERIAL_PORT_MODULE,     0x1C   Container of one or more serial ports
                     PARENT,                 0x1D   Reference to parent for multi-parent support
                     PHY_PORT,               0x1E   Physical port
                     IO_EXPANDER,            0x1F   RAID card
                     CABLE,                  0x20   Cable/Interconnect
                     FAN_MUX                 0x29   Fan multiplexer card
                     PCI_EXPRESS,            0x32   PCI express card on (PEN)
                     FLASH_DIMM,             0x33   Used for SPD devices that matches the silkscreen of the DIMM slot
                     RACK,                   0x50   Rack
                     PLATFORM,               0x51   Generic Platform like rack mounted server/appliance
                     DATAPLEX,               0x52   DataPlex
                     OTHER,                  0x53   Other unknown etc.
                     PERIPHERAL_MODULE,      0x54 
                     SYSTEM_BOARD,           0x55   System board
                     PROCESSOR_MODULE,       0x56 
                     BACK_PANEL,             0x57 
                     POWER_SYSTEM_BOARD,     0x58 
                     STORAGE_BACKPLANE,      0x59   Drive back plane
                     PROC_BOARD,             0x5A   Holds 1 or more processors
                     POWER_DI,               0x5B   Power mgt / power distribution board
                     CHASSIS_BACK_PANEL,     0x5C 
                     SUB_CHASSIS,            0x5D 
                     OTHER_CHASSIS_BOARD,    0x5E 
                     DEVICE_MODULE,          0x5F 
                     REMOTE_DEVICE,          0x60   Remote mgt communication device
                     EXTERNAL_ENVIRONMENT,   0x61   Such as external temp sensor for outside box temps
                     PROC_MEMORY_MODULE,     0x62   Processors and memory on same module"
                   ::= { componentLEDsDetailsEntry 1 }

       componentLEDsDetailsIndex  OBJECT-TYPE
                   SYNTAX  INTEGER
                   ACCESS  read-only
                   STATUS  mandatory
                   DESCRIPTION
                   "Each component may have one or more LEDs and data
                   associated with it, and this index object identifies the
                   particular instance."
                   ::= { componentLEDsDetailsEntry 2 }

       componentLEDsDetailsComponentType OBJECT-TYPE
                   SYNTAX  OCTET STRING
                   ACCESS  read-only
                   STATUS  mandatory
                   DESCRIPTION
                   "The type of the component/subcomponent grouping for this LED."
                   ::= { componentLEDsDetailsEntry 3 }

       componentLEDsDetailsLabel OBJECT-TYPE
                   SYNTAX  OCTET STRING
                   ACCESS  read-only
                   STATUS  mandatory
                   DESCRIPTION
                   "The text description of the LED."
                   ::= { componentLEDsDetailsEntry 4 }

       componentLEDsDetailsState OBJECT-TYPE
                   SYNTAX  INTEGER {
                      off(0),
                      on(1),
                      blinking(2)
                   }
                   ACCESS  read-only
                   STATUS  mandatory
                   DESCRIPTION
                   "The current state of the LED."
                   ::= { componentLEDsDetailsEntry 5 }

       componentLEDsDetailsLocation OBJECT-TYPE
                   SYNTAX  OCTET STRING
                   ACCESS  read-only
                   STATUS  mandatory
                   DESCRIPTION
                   "The physical location of this LED on the hardware."
                   ::= { componentLEDsDetailsEntry 6 }

      -- *************************************************************************
      -- componentLEDsDetailsTableCacheTimeout
      -- *************************************************************************
      componentLEDsDetailsTableCacheTimeout OBJECT-TYPE
               SYNTAX  INTEGER
               ACCESS  read-only
               STATUS  mandatory
               DESCRIPTION
               "The timeout value (in seconds) of the cached data for the
               table, componentLEDsDetailsTable.
               This value is static (constant) and cannot be set."
               ::= { componentLEDs 10 }
    -- ************************************************************************
    -- backupRestore
    -- ************************************************************************
	backupRestore OBJECT IDENTIFIER ::= { components 42 }

    backupRestoreAction         OBJECT-TYPE
                                SYNTAX  INTEGER {
                                  backup(0),
                                  restore(1),
	                          restoreAndRestart(2)
                                }
                                ACCESS  read-write
                                STATUS  mandatory
                                DESCRIPTION
                                "Starts the backup or restore operation.
				It is intended to be write-only.
				NOTE: This function is only available for SNMPv3."
                                ::= { backupRestore 1 }

    backupRestoreStatus		OBJECT-TYPE
                                SYNTAX INTEGER {
				  ready(0),
				  pending(1)
				}
				ACCESS read-only
				STATUS mandatory
				DESCRIPTION
				"Get the status of the last backup/restore action which was
				initiated through SNMP.
				NOTE: This function is only available for SNMPv3."
				::= { backupRestore 2 }

	backupRestoreMessage    OBJECT-TYPE
                                SYNTAX OCTET STRING
                                ACCESS  read-only
                                STATUS  mandatory
                                DESCRIPTION
                                "Get the status message of the last backup/restore action which was
                                initiated through SNMP.
				NOTE: This function is only available for SNMPv3."
                                ::= { backupRestore 3 }

	backupRestoreURI        OBJECT-TYPE
                                SYNTAX  OCTET STRING (SIZE(0..254))
                                ACCESS  read-write
                                STATUS  mandatory
                                DESCRIPTION
                                "Contains the fully qualified remote location of the file.
				 A fully qualified remote location contains a supported
				 protocol followed by a colon and two slashes (//), userid and
				 password separated by a colon for login authentication, an
				 @ sign, followed by the hostname or IP address of the
				 server where the packet file resides, followed by an optional
				 port number to the hostname, and the full pathname to the file.
				 Note that if the port number is specified, it must be
				 separated with the hostname (or IP address) by a colon.
				 The MM currently supports the following protocols:
				 TFTP, FTP, HTTP and HTTPS.
				 The complete format of a fully qualified remote location is:
				 <protocol>://<userid:password>@<hostname:port>/<pathname>
				 An example of a fully qualified remote location can be:
				 ftp://USERID:PASSW0RD@192.168.0.2:30045/tmp/cmd.bkp
				 where the ftp protocol will be used for transferring the file in
				 this location, username is USERID,  password is
				 PASSW0RD, host IP address is 192.168.0.2, port number is
				 30045, and the full pathname for the packet file is /tmp/cmd.bkp.
				 Some protocols do not need the username, password, and
				 the port number, so the minimum requirement for a fully
				 qualified location can be:<protocol>://<hostname>/<pathname>.
				 Note:When using SFTP, only an RSA fingerprint is supported.
                                 An example of a qualified location can be:
                                 <protocol>://[<user>[:password][;fingerprint=<host>]@]<host>
                                 [:<port>]/<path>/<to>/<file>
				 NOTE: This function is only available for SNMPv3."
                                ::= { backupRestore 4 }

	backupRestorePassword   OBJECT-TYPE
                                SYNTAX  OCTET STRING (SIZE(0..63))
                                ACCESS  read-write
                                STATUS  mandatory
                                DESCRIPTION
                                "Password used for the encryption/decryption of the sensitive data
				 in the backup file.
				 It is intended to be write-only.
				NOTE: This function is only available for SNMPv3."
                                ::= { backupRestore 5 }

        backupRestoreLogURI     OBJECT-TYPE
                                SYNTAX  OCTET STRING (SIZE(0..254))
                                ACCESS  read-write
                                STATUS  mandatory
                                DESCRIPTION
                                "Indicates the URI address where the log file will be put. It will be used only
				 if the backupRestoreLogPush will be set on push.
				 Contains the fully qualified remote location of the file.
				 A fully qualified remote location contains a supported
				 protocol followed by a colon and two slashes (//), userid and
				 password separated by a colon for login authentication, an
				 @ sign, followed by the hostname or IP address of the
				 server where the packet file will reside, followed by an optional
				 port number to the hostname, and the full pathname to the file.
				 Note that if the port number is specified, it must be
				 separated with the hostname (or IP address) by a colon.
				 The MM currently supports the following protocols:
				 TFTP, FTP, HTTP and HTTPS.
				 The complete format of a fully qualified remote location is:
				 <protocol>://<userid:password>@<hostname:port>/<pathname>
				 An example of a fully qualified remote location can be:
				 ftp://USERID:PASSW0RD@192.168.0.2:30045/tmp/restore.log
				 where the ftp protocol will be used for transferring the file in
				 this location, username is USERID,  password is
				 PASSW0RD, host IP address is 192.168.0.2, port number is
				 30045, and the full pathname for the packet file is /tmp/restore.log.
				 Some protocols do not need the username, password, and
				 the port number, so the minimum requirement for a fully
				 qualified location can be:<protocol>://<hostname>/<pathname>.
				 Note: When using SFTP, only an RSA fingerprint is supported.
                                 An example of a qualified location can be:
                                 <protocol>://[<user>[:password][;fingerprint=<host>]@]<host>
                                 [:<port>]/<path>/<to>/<file>

				 NOTE: This function is available only for SNMPv3."
                                ::= { backupRestore 6 }

	backupRestoreLogPush    OBJECT-TYPE
                                SYNTAX  INTEGER {
                                  noPush(0),
				  push(1)
                                }
                                ACCESS  read-write
                                STATUS  mandatory
                                DESCRIPTION
                                "Causes the restore operation to push the log to the URI address.
				NOTE: This can be used when restoring without restarting.
				NOTE: This function is only available for SNMPv3."
                                ::= { backupRestore 7 }


    -- ************************************************************************
    -- FFDC Service
    -- ************************************************************************

    bladeServiceData  OBJECT IDENTIFIER ::= { service 3 }

    bladeServiceDataTable OBJECT-TYPE
                     SYNTAX  SEQUENCE OF BladeServiceDataEntry
                     ACCESS  not-accessible
                     STATUS  mandatory
                     DESCRIPTION
                     "Table of blade service data information."
                     ::= { bladeServiceData 1 }

       bladeServiceDataEntry OBJECT-TYPE
                     SYNTAX BladeServiceDataEntry
                     ACCESS  not-accessible
                     STATUS  mandatory
                     DESCRIPTION
                     "Blade service data entry"
                     INDEX { serviceDataIndex }
                     ::= { bladeServiceDataTable 1 }


       BladeServiceDataEntry ::= SEQUENCE {
                   serviceDataIndex INTEGER,
                   serviceDataBladeId INTEGER,
                   serviceDataBladeExists INTEGER,
                   serviceDataBladePowerState INTEGER,
                   serviceDataBladeName OCTET STRING,
                   serviceDataDumpInitiate INTEGER,
                   serviceDataDumpRetrieve INTEGER,
                   serviceDataDumpCapabilityMask OCTET STRING,
                   serviceDataDumpInProgress INTEGER
                   }

       serviceDataIndex  OBJECT-TYPE
                   SYNTAX  INTEGER
                   ACCESS  read-only
                   STATUS  mandatory
                   DESCRIPTION
                   "Blade service date index."
                   ::= { bladeServiceDataEntry 1 }

       serviceDataBladeId   OBJECT-TYPE
                   SYNTAX  INTEGER {
                       blade1(1),
                       blade2(2),
                       blade3(3),
                       blade4(4),
                       blade5(5),
                       blade6(6),
                       blade7(7),
                       blade8(8),
                       blade9(9),
                       blade10(10),
                       blade11(11),
                       blade12(12),
                       blade13(13),
                       blade14(14)
                     }
                   ACCESS  read-only
                   STATUS  mandatory
                   DESCRIPTION
                   "The numeric blade ID."
                   ::= { bladeServiceDataEntry 2 }

       serviceDataBladeExists OBJECT-TYPE
                   SYNTAX  INTEGER {
                     false(0),
                     true(1)
                   }
                   ACCESS  read-only
                   STATUS  mandatory
                   DESCRIPTION
                   "Indicates whether the blade specified exists or not."
                   ::= { bladeServiceDataEntry 3 }

       serviceDataBladePowerState OBJECT-TYPE
                   SYNTAX  INTEGER {
                       off(0),
                       on(1),
                       standby(3),
                       hibernate(4),
                       unknown(255)
                   }
                   ACCESS  read-only
                   STATUS  mandatory
                   DESCRIPTION
                   "Indicates whether the blade specified is powered on or not. 
                    If the MM is experiencing a communication problem with the blade, 
                    the state may be returned as unknown(255)"
                   ::= { bladeServiceDataEntry 4 }

       serviceDataBladeName OBJECT-TYPE
                   SYNTAX  OCTET STRING
                   ACCESS  read-only
                   STATUS  mandatory
                   DESCRIPTION
                   "The name of the blade as a string."
                   ::= { bladeServiceDataEntry 5 }

       serviceDataDumpInitiate OBJECT-TYPE
                   SYNTAX  INTEGER {
                     processorDump(1),
                     platformDump(2),
                     partitionDump(3),
                     serviceData(4)
                   }
                   ACCESS  read-write
                   STATUS  mandatory
                   DESCRIPTION
                   "Initiates a type of dump collection to be initiated for the blade.

                   NOTE: Not all blades support this, please check serviceDataDumpCapabilityMask
                   OID to see if the action is supported on this blade. 

                   When the dump file is created, the node transfers it to the /tftproot/service directory 
                   on the CMM. Only one file can be moved to this directory at a time, so please use the fileManagement 
                   MIB information to check if the file has been completed.

                   NOTE: Value returned for the GET command is meaningless
                   for this MIB object."
                   ::= { bladeServiceDataEntry 7 }

       serviceDataDumpRetrieve OBJECT-TYPE
                   SYNTAX INTEGER {
                     processorDump(1),
                     platformDump(2),
                     partitionDump(3),
                     serviceData(4)
                   }
                   ACCESS read-write
                   STATUS mandatory
                   DESCRIPTION
                   "Retrieve a type of service data file from blade to MM.

                   NOTE: This OID only is valid for the last four bit mask designations listed
                   in the serviceDataDumpCapabilityMask OID. 

                   The dump file is transfered to the /tftproot/service directory 
                   on the CMM. Only one file can be moved to this directory at a time, 
                   so please use the fileManagement MIB information to check if the file has been completed.

                   NOTE: Value returned for the GET command is meaningless
                   for this MIB object."
                   ::= { bladeServiceDataEntry 8 }

       serviceDataDumpCapabilityMask OBJECT-TYPE
                   SYNTAX  OCTET STRING
                   ACCESS  read-only
                   STATUS  mandatory
                   DESCRIPTION
                   "Indicates whether the blade has the capability to trigger service data and if so,
                   which operations are supported and whether the file can be transferred to the MM
                   from the blade.
                   The values and meanings are as follows:
                   0000 0000 means this blade does not support any at all.

                   0000 0001 means this blade supports 'processor' type and the file remains on the blade.
                   0000 0010 means this blade supports 'platform' type and the file remains on the blade
                   0000 0100 means this blade supports 'partition' type and the file remians on the blade

                   0000 1000 means this blade supports 'processor' type and the file can be transferred to the MM.
                   0001 0000 means this blade supports 'platform' type and the file can be transferred to the MM.
                   0010 0000 means this blade supports 'partition' type and the file can be transferred to the MM
                   0100 0000 means this blade supports 'serviceData' type and the file can be transferred to the MM
                   For example, the returned value of 01111000 means this blade supports 'processor','platform',
                   'partition' and 'serviceData' types, and the file can be transferred to the MM"
                   ::= { bladeServiceDataEntry 9 }

       serviceDataDumpInProgress OBJECT-TYPE
                   SYNTAX INTEGER {
                     inProgress(1),
                     notInProgress(2),
                     unknown(255)
                   }
                   ACCESS read-only
                   STATUS mandatory
                   DESCRIPTION
                   "An indicator as to whether a blade dump is in progress for the specified blade.
                    This object ONLY applies to dumps that can be triggered by the MM and where the
                    dump file is transferred to the MM filesystem upon completion. See the
                    serviceDataDumpCapabilityMask object for support levels. The flag that this MIB object
                    represents will be set on when the IPMI command is sent to the blade indicating 'init dump'
                    and will be cleared upon receiving the valid dump file from the blade or the
                    creation of the text file indicating the problem encountered.
                    If it cannot be determined if the dump is in progress, the unknown(255) value is returned."
                   ::= { bladeServiceDataEntry 10 }

serviceAdvisor   OBJECT IDENTIFIER ::= { service 4 }

 autoCallHomeSetup   OBJECT IDENTIFIER ::= { serviceAdvisor 1 }

     acceptLicenseAgreement OBJECT-TYPE
         SYNTAX INTEGER {
             disabled(0),
             enabled(1)
         }
         ACCESS read-write
         STATUS mandatory
         DESCRIPTION
         "Accept Terms and Conditions of MM Service Advisor. The user will have to accept the terms and conditions
         before Service Advisor can send diagnostic data to support personnel. If MM configuration
         is reset to defaults, the user will have to accept the terms and conditions again before they can
         enable Service Advisor. 

         A GET of this object may return disabled(0) or enabled(1), depending upon the current state. However,
         only enabled(1) is accepted on a SET in order to accept the license agreement. A SET of disabled(0)
         will return noSuchValue and is not allowed."
         ::= {autoCallHomeSetup 1}

     serviceAdvisorEnable OBJECT-TYPE
         SYNTAX INTEGER {
             disabled(0),
             enabled(1)
         }
         ACCESS read-write
         STATUS mandatory
         DESCRIPTION
         "Disable/Enable Support. The User Agreement must be accepted and the contact information
         must be set before the Support function of Service Advisor can be enabled."
         ::= {autoCallHomeSetup 2}

serviceSupportCenter  OBJECT IDENTIFIER ::= {serviceAdvisor 2}
     supportCenter OBJECT-TYPE
         SYNTAX OCTET STRING
         ACCESS read-write
         STATUS mandatory
         DESCRIPTION
         "The country code for the Support Center. 2 character ISO country code."
         ::= {serviceSupportCenter 1}

contactInformation  OBJECT IDENTIFIER ::= {serviceAdvisor 3}

     companyName OBJECT-TYPE
         SYNTAX OCTET STRING
         ACCESS read-write
         STATUS mandatory
         DESCRIPTION
         " The organization/company name of the contact person. 1-30 characters."
         ::= {contactInformation 1}

     contactName OBJECT-TYPE
         SYNTAX OCTET STRING
         ACCESS read-write
         STATUS mandatory
         DESCRIPTION
         "The name of the contact person.1-30 characters."
         ::= {contactInformation 2}

     phoneNumber OBJECT-TYPE
         SYNTAX OCTET STRING
         ACCESS read-write
         STATUS mandatory
         DESCRIPTION
         "The phone of the contact person. 5-30 characters."
         ::= {contactInformation 3}

     emailAddress OBJECT-TYPE
         SYNTAX OCTET STRING
         ACCESS read-write
         STATUS mandatory
         DESCRIPTION
         "The email of the contact person. It must contain '@' and dot '.' in form userid@hostname (130 characters maximum).
         The userid can be alphanumeric characters, '.', '-', or '_' but must begin and end with alphanumeric characters.
         The hostname can be alphanumeric characters, '.', '-', or '_'. It must contain at least two domain items.
         Every domain item should begin and end with alphanumeric character, and the last domain item should be 2-20 alphabetic characters."
         ::= {contactInformation 4}

     address OBJECT-TYPE
         SYNTAX OCTET STRING
         ACCESS read-write
         STATUS mandatory
         DESCRIPTION
         "The address of the machine location. The information in this field should be of sufficient detail to allow someone to
          quickly find the chassis when necessary. 1-30 characters."
         ::= {contactInformation 5}

     city OBJECT-TYPE
         SYNTAX OCTET STRING
         ACCESS read-write
         STATUS mandatory
         DESCRIPTION
         "The city of the machine location. 1-30 characters."
         ::= {contactInformation 6}

     state OBJECT-TYPE
         SYNTAX OCTET STRING
         ACCESS read-write
         STATUS mandatory
         DESCRIPTION
         "The state of the machine location. 2-3 characters."
         ::= {contactInformation 7}

     postalCode OBJECT-TYPE
         SYNTAX OCTET STRING
         ACCESS read-write
         STATUS mandatory
         DESCRIPTION
         "The postal code of the location for this system. 1-10 characters, only alphanumeric and dash characters are valid."
         ::= {contactInformation 8}

     phoneNumberExt OBJECT-TYPE
         SYNTAX OCTET STRING
         ACCESS read-write
         STATUS mandatory
         DESCRIPTION
         "The phone number extension of the contact person. 1-30 characters."
         ::= {contactInformation 9}

     altContactName OBJECT-TYPE
         SYNTAX OCTET STRING
         ACCESS read-write
         STATUS mandatory
         DESCRIPTION
         "The name of the alternate contact person.1-30 characters."
         ::= {contactInformation 10}

     altPhoneNumber OBJECT-TYPE
         SYNTAX OCTET STRING
         ACCESS read-write
         STATUS mandatory
         DESCRIPTION
         "The phone of the alternate contact person. 5-30 characters."
         ::= {contactInformation 11}

     altPhoneNumberExt OBJECT-TYPE
         SYNTAX OCTET STRING
         ACCESS read-write
         STATUS mandatory
         DESCRIPTION
         "The phone number extension of the alternate contact person. 1-30 characters."
         ::= {contactInformation 12}

     altEmailAddress OBJECT-TYPE
         SYNTAX OCTET STRING
         ACCESS read-write
         STATUS mandatory
         DESCRIPTION
         "The email of the alternate contact person. It must contain '@' and dot '.' in form userid@hostname (130 characters maximum).
         The userid can be alphanumeric characters, '.', '-', or '_' but must begin and end with alphanumeric characters.
         The hostname can be alphanumeric characters, '.', '-', or '_'. It must contain at least two domain items.
         Every domain item should begin and end with alphanumeric character, and the last domain item should be 2-20 alphabetic characters."
         ::= {contactInformation 13}

httpProxyConfig  OBJECT IDENTIFIER ::= {serviceAdvisor 4}

    httpProxyEnable OBJECT-TYPE
        SYNTAX INTEGER{
           disabled(0),
           enabled(1)
        }
        ACCESS read-write
        STATUS mandatory
        DESCRIPTION
        "Disable/Enable of the HTTP Proxy. Select Enable to use the proxy for call home
         connections from the MM to support. HTTP Proxy is used by the MM when it is not connected to the internet directly."
        ::= {httpProxyConfig 1}

    httpProxyLocation OBJECT-TYPE
        SYNTAX OCTET STRING
        ACCESS read-write
        STATUS mandatory
        DESCRIPTION
        "Fully qualified host name or IP address of the HTTP Proxy. Maximum of 63 characters."
        ::= {httpProxyConfig 2}

    httpProxyPort OBJECT-TYPE
        SYNTAX INTEGER
        ACCESS read-write
        STATUS mandatory
        DESCRIPTION
        "The port number of the HTTP Proxy. An integer value from 1 to 65535."
        ::= {httpProxyConfig 3}

    httpProxyUserName OBJECT-TYPE
        SYNTAX OCTET STRING
        ACCESS read-write
        STATUS mandatory
        DESCRIPTION
        "User Name of the HTTP Proxy. A maximum of 30 characters string without spaces."
        ::= {httpProxyConfig 4}

    httpProxyPassword OBJECT-TYPE
        SYNTAX OCTET STRING
        ACCESS read-write
        STATUS mandatory
        DESCRIPTION
        "Password of the HTTP Proxy. A maximum of 15 characters string without spaces."
        ::= {httpProxyConfig 5}

   activityLogs   OBJECT IDENTIFIER ::= { serviceAdvisor 5}

    activityLogTable  OBJECT-TYPE
                      SYNTAX  SEQUENCE OF ActivityLogEntry
                      ACCESS  not-accessible
                     STATUS  mandatory
                      DESCRIPTION
                      "Table of Service Advisor Activity Log entries information. This table displays the last five
                      events that were generated by the system or user that are called home. The entries are displayed in
                      reverse chronological order (most recent call home entry first). For any events that happen with same
                      Date/Time, only one event will be called home. If a call home event that is already in the activity
                      log is triggered again on the same event source, it will not be called home again unless the prior entry has
                      been acknowledged as corrected or 120 hours (5 days) have passed since it initially occurred and was called home. "
                     ::= { activityLogs 1 }

      activityLogEntry OBJECT-TYPE
                    SYNTAX   ActivityLogEntry
                    ACCESS  not-accessible
                    STATUS  mandatory
                    DESCRIPTION
                    "Activity Log table entry. Each entry has the result of the FTP/TFTP Server attempt,
                    the event ID, event source, date and time that event occured, and a text message."
                    INDEX { activityLogIndex }
                    ::= { activityLogTable 1 }

      ActivityLogEntry ::= SEQUENCE {
                 activityLogIndex INTEGER,
                 activityLogString OCTET STRING,
                 activityLogAcknowledge INTEGER,
                 activityLogAttribute OCTET STRING,
                 activityLogCommonEventID OCTET STRING
                  }

      activityLogIndex  OBJECT-TYPE
                  SYNTAX  INTEGER
                  ACCESS  read-only
                  STATUS  mandatory
                  DESCRIPTION
                  "The Activity Log index number.
                  For consistent results, view as a table and not as individual entries."
                  ::= { activityLogEntry 1 }

      activityLogString OBJECT-TYPE
                  SYNTAX  OCTET STRING
                  ACCESS  read-only
                  STATUS  mandatory
                  DESCRIPTION
                  "A string of data detailing one Activity Log entry. The text message is from the original entry in the event log.
                  For consistent results, view as a table and not as individual entries."
                  ::= { activityLogEntry 2 }

     activityLogAcknowledge OBJECT-TYPE
                  SYNTAX INTEGER{
                    no(0),
                    yes(1) }
                  ACCESS  read-write
                  STATUS  mandatory
                  DESCRIPTION
                  "The acknowledgement of one Activity Log entry as corrected. This field allows the users to set a reminder next to
                  certain events to indicate their awareness of the issue. Checking the acknowledge flag will not cause the event to be removed
                  from the log. This log is not cleared, so the acknowledge flag can be used to indicate a problem can be ignored. This field
                  can be also used to override the 120 hour (5 day) filtering of reports via FTP/TFTP Server of Service Data."
                  ::= { activityLogEntry 3 }

      activityLogAttribute OBJECT-TYPE
                  SYNTAX  OCTET STRING
                  ACCESS  read-only
                  STATUS  mandatory
                  DESCRIPTION
                  "A string of data detailing one Activity Log entry's attribute. Status PENDING indicates that the system
                  is preparing for the event to be called home by collecting data about the systems state. A SUCCESS state
                  indicates that the problem was successfully transmitted to FTP/TFTP Server. The FAILED state indicates that the attempt
                  to transmit the event information was not successful. Additional information may be found in the Event Log.
                  The event ID, event source , date and time are all information from the original entry in the event log.
                  The acknowledged as corrected field is a reminder to certain events to indicate their awareness of the issue."
                  ::= { activityLogEntry 4 }

     activityLogCommonEventID OBJECT-TYPE
                  SYNTAX  OCTET STRING
                  ACCESS  read-only
                  STATUS  mandatory
                  DESCRIPTION
                  "Activity Log Entry Common Event ID of an event ID."
                  ::= { activityLogEntry 5 }

     -- ********************************************************************************
     -- autoftp
     -- ********************************************************************************
     --
       autoFTPSetup  OBJECT IDENTIFIER ::= { service 5 }

        autoFTPCallMode    OBJECT-TYPE
                      SYNTAX  INTEGER {
                        disabled(0),
                        ftp(1),
                        tftp(2)
                      }
                      ACCESS  read-write
                      STATUS  mandatory
                      DESCRIPTION
                      "This field specifies the automated problem reporting mode. Automated problem reporting mode allows the MM to automatically put
                      service data to a specified server when a call home event is detected. For any call home events that happen with same Date/Time,
                      only one event will be reported. The system will also wait for an interval of 120 hours (5 days) before another identical event
                      can be sent for the same failed component."
                      ::= { autoFTPSetup 1 }

          autoFTPCallAddr  OBJECT-TYPE
                      SYNTAX  OCTET STRING
                      ACCESS  read-write
                      STATUS  mandatory
                      DESCRIPTION
                      "This field specifies the remote server address of FTP and TFTP. It should be fully qualified hostname or IP address."
                       ::= { autoFTPSetup 2 }

         autoFTPCallPort  OBJECT-TYPE
                        SYNTAX  INTEGER
                        ACCESS  read-write
                        STATUS  mandatory
                        DESCRIPTION
                        "This field specifies the port on remote FTP/TFTP server for data transmission."
                       ::= { autoFTPSetup 3 }

         autoFTPCallUserID  OBJECT-TYPE
                      SYNTAX  OCTET STRING
                      ACCESS  read-write
                      STATUS  mandatory
                      DESCRIPTION
                      "This field specifies the user account to login remote FTP server."
                       ::= { autoFTPSetup 4 }

          autoFTPCallPassword   OBJECT-TYPE
                      SYNTAX  OCTET STRING
                      ACCESS  read-write
                      STATUS  mandatory
                      DESCRIPTION
                      "This field specifies the password to login remote FTP server."
                       ::= { autoFTPSetup 5 }

-- ********************************************************************************
--    Call Home Exclusion List
-- ********************************************************************************

callHomeExclusionEvents OBJECT IDENTIFIER ::= {  service 6}

    readCallHomeExclusionEventTable  OBJECT-TYPE
                      SYNTAX  SEQUENCE OF ReadCallHomeExclusionEventEntry
                      ACCESS  not-accessible
                      STATUS  mandatory
                      DESCRIPTION
                      "Table of Call Home Exclusion Event entries information."
                     ::= { callHomeExclusionEvents 1 }

      readCallHomeExclusionEventEntry OBJECT-TYPE
                    SYNTAX   ReadCallHomeExclusionEventEntry
                    ACCESS  not-accessible
                    STATUS  mandatory
                    DESCRIPTION
                    "Call Home Exclusion Event table entry"
                    INDEX { readCallHomeExclusionEventIndex }
                    ::= { readCallHomeExclusionEventTable 1 }

      ReadCallHomeExclusionEventEntry::= SEQUENCE {
                 readCallHomeExclusionEventIndex INTEGER,
                 readCallHomeExclusionEventID OCTET STRING,
                 readCallHomeExclusionCommonEventID OCTET STRING
                  }

     readCallHomeExclusionEventIndex  OBJECT-TYPE
                  SYNTAX  INTEGER
                  ACCESS  read-only
                  STATUS  mandatory
                  DESCRIPTION
                  "The index number of one Call Home Exclusion Event.
                  For consistent results, view as a table and not as individual entries."
                  ::= { readCallHomeExclusionEventEntry 1 }

      readCallHomeExclusionEventID OBJECT-TYPE
                  SYNTAX  OCTET STRING
                  ACCESS  read-only
                  STATUS  mandatory
                  DESCRIPTION
                  "The Event ID of one Call Home Exclusion Event entry.
                  For consistent results, view as a table and not as individual entries."
                  ::= { readCallHomeExclusionEventEntry 2 }

       readCallHomeExclusionCommonEventID OBJECT-TYPE
                  SYNTAX  OCTET STRING
                  ACCESS  read-only
                  STATUS  mandatory
                  DESCRIPTION
                  "The Common Event ID of one Call Home Exclusion Event entry.
                  For consistent results, view as a table and not as individual entries."
                  ::= { readCallHomeExclusionEventEntry 3 }

      addCallHomeExclusionEvent  OBJECT-TYPE
                      SYNTAX  OCTET STRING
                      ACCESS  read-write
                      STATUS  mandatory
                      DESCRIPTION
                      "Add one call home Event ID into the Call Home Exclusion List.
                      The Event ID is an 8-digit hexadecimal number (0-F) with an optional prefix of '0x' or '0X'.
                      An Event can not be added into the exclusion list if autoFtpMode is disabled.
                      If Service Advisor Terms and Conditions are accepted, an event can be added into the exclusion list.
                      NOTE: Value returned for the GET command is meaningless for this MIB object."
                     ::= { callHomeExclusionEvents 2}

    rmCallHomeExclusionEvent  OBJECT-TYPE
                      SYNTAX  OCTET STRING
                      ACCESS  read-write
                      STATUS  mandatory
                      DESCRIPTION
                      "Remove one call home Event ID from the Call Home Exclusion List.
                      The Event ID is an 8-digit hexadecimal number (0-F) with an optional prefix of '0x' or '0X'.
                      An event on the exclusion list can not be removed if autoFtpMode is disabled.
                      If Service Advisor Terms and Conditions are accepted, an event on the exclusion list can be removed.

                      NOTE: Value returned for the GET command is meaningless for this MIB object."
                     ::= { callHomeExclusionEvents 3}

    rmAllCallHomeExclusionEvent  OBJECT-TYPE
                      SYNTAX  INTEGER {
                      execute(1)
                      }
                      ACCESS  read-write
                      STATUS  mandatory
                      DESCRIPTION
                      "Remove all Event IDs from the Call Home Exclusion List.
                      Events on the exclusion list can not be removed if autoFtpMode is disabled.
                      If Service Advisor Terms and Conditions are accepted, events on the exclusion list can be removed.

                      NOTE: Value returned for the GET command is meaningless for this MIB object."
                     ::= { callHomeExclusionEvents 4}


-- ********************************************************************************
--    Component Service Reset 
-- ********************************************************************************

    componentPowerServiceReset  OBJECT IDENTIFIER ::= { service 10 }

    bladePowerServiceResetTable OBJECT-TYPE
                     SYNTAX  SEQUENCE OF BladePowerServiceResetEntry
                     ACCESS  not-accessible
                     STATUS  mandatory
                     DESCRIPTION
                     "A table providing aux power status and the ability
                      to perform a virtual reseat or hard restart of a blade."
                     ::= { componentPowerServiceReset 1 }

       bladePowerServiceResetEntry OBJECT-TYPE
                     SYNTAX BladePowerServiceResetEntry
                     ACCESS  not-accessible
                     STATUS  mandatory
                     DESCRIPTION
                     "Blade power service reset entry"
                     INDEX { bladePowerServiceResetIndex }
                     ::= { bladePowerServiceResetTable 1 }

       BladePowerServiceResetEntry ::= SEQUENCE {
                   bladePowerServiceResetIndex INTEGER,
                   bladePowerServiceResetBladeId INTEGER,
                   bladePowerServiceResetStatus INTEGER,
                   bladePowerServiceResetCmd INTEGER
                   }

       bladePowerServiceResetIndex  OBJECT-TYPE
                   SYNTAX  INTEGER
                   ACCESS  read-only
                   STATUS  mandatory
                   DESCRIPTION
                   "Blade power service reset index."
                   ::= { bladePowerServiceResetEntry 1 }

       bladePowerServiceResetBladeId   OBJECT-TYPE
                   SYNTAX  INTEGER {
                       blade1(1),
                       blade2(2),
                       blade3(3),
                       blade4(4),
                       blade5(5),
                       blade6(6),
                       blade7(7),
                       blade8(8),
                       blade9(9),
                       blade10(10),
                       blade11(11),
                       blade12(12),
                       blade13(13),
                       blade14(14)
                     }
                   ACCESS  read-only
                   STATUS  mandatory
                   DESCRIPTION
                   "The numeric blade slot number."
                   ::= { bladePowerServiceResetEntry 2 }

       bladePowerServiceResetStatus   OBJECT-TYPE
                   SYNTAX  INTEGER {
                       auxPowerOff(0),
                       auxPowerOn(1)
                     }
                   ACCESS  read-only
                   STATUS  mandatory
                   DESCRIPTION
                   "Status of the aux power.  A value of auxPowerOff(0) indicates
                   that the blade aux power is off.  A value of
                   auxPowerOn(1) indicates that the blade aux power is on."
                   ::= { bladePowerServiceResetEntry 3 }

       bladePowerServiceResetCmd   OBJECT-TYPE
                   SYNTAX  INTEGER {
                       noOperation(0),
                       resetVirtualReseatOperation(1),
                       resetHardRestartOperation(2)
                     }
                   ACCESS  read-write
                   STATUS  mandatory
                   DESCRIPTION
                   "NOTE: Do not perform this service reset operation on a node that is
                   currently in a maintenance mode state. See bladeHealthState in
                   bladeSystemStatusTable for maintMode(12) value.


                   To reset the auxiliary power on a blade component, set this object to
                   resetVirtualReseatOperation(1). This will toggle the auxiliary 
                   power to the blade and simulate a physical removal and insertion.
                   During the operation, auxiliary power is removed from the component 
                   and is then restored. For nodes, the power state will remain off and the 
                   user will need to manually power on the node.  

                   To perform a hard restart on the blade component, set this object to 
                   resetHardRestartOperation(2). This will toggle the reset line to the 
                   service processor causing it to re-initialize. The service processor on 
                   the component is directly reset, but the power state of the component 
                   will not be affected by this operation.

                   This object is intended to be write-only.

                   The component will experience a temporary loss of communication and the power 
                   state will change. Prior to executing this action, perform any operations needed
                   to protect user data.

                   Reading this object will always return the value of noOperation(0)."
                   ::= { bladePowerServiceResetEntry 4 }

    smPowerServiceResetTable OBJECT-TYPE
                     SYNTAX  SEQUENCE OF SmPowerServiceResetEntry
                     ACCESS  not-accessible
                     STATUS  mandatory
                     DESCRIPTION
                     "A table providing aux power status and the ability
                      to perform a virtual reseat or hard restart of a switch."
                     ::= { componentPowerServiceReset 2 }

       smPowerServiceResetEntry OBJECT-TYPE
                     SYNTAX  SmPowerServiceResetEntry
                     ACCESS  not-accessible
                     STATUS  mandatory
                     DESCRIPTION
                     "Switch module power service reset entry"
                     INDEX { smPowerServiceResetIndex }
                     ::= { smPowerServiceResetTable 1 }

       SmPowerServiceResetEntry ::= SEQUENCE {
                   smPowerServiceResetIndex INTEGER,
                   smPowerServiceResetSwitchId INTEGER,
                   smPowerServiceResetStatus INTEGER,
                   smPowerServiceResetCmd INTEGER
                   }

       smPowerServiceResetIndex  OBJECT-TYPE
                   SYNTAX  INTEGER
                   ACCESS  read-only
                   STATUS  mandatory
                   DESCRIPTION
                   "Switch module power service reset index."
                   ::= { smPowerServiceResetEntry 1 }

       smPowerServiceResetSwitchId   OBJECT-TYPE
                   SYNTAX  INTEGER {
                       switch1(1),
                       switch2(2),
                       switch3(3),
                       switch4(4)
                     }
                     ACCESS  read-only
                     STATUS  mandatory
                     DESCRIPTION
                     "The switch module numeric identifier."
                   ::= { smPowerServiceResetEntry 2 }

       smPowerServiceResetStatus   OBJECT-TYPE
                   SYNTAX  INTEGER {
                       auxPowerOff(0),
                       auxPowerOn(1)
                     }
                   ACCESS  read-only
                   STATUS  mandatory
                   DESCRIPTION
                   "Status of the aux power power.  A value of auxPowerOff(0) indicates
                   that the switch aux power is off.  A value of
                   auxPowerOn(1) indicates that the switch aux power is on."
                   ::= { smPowerServiceResetEntry 3 }

       smPowerServiceResetCmd   OBJECT-TYPE
                   SYNTAX  INTEGER {
                       noOperation(0),
                       resetVirtualReseatOperation(1)
                     }
                   ACCESS  read-write
                   STATUS  mandatory
                   DESCRIPTION
                   "To reset the auxiliary power on a switch component, set this object to
                   resetVirtualReseatOperation(1). This will toggle the auxiliary 
                   power to the switch and simulate a physical removal and insertion.  
                   During the operation, auxiliary power is removed from the component 
                   and is then restored. For IOMs, the power state will be on after the  
                   operation completes.

                   To perform a hard restart on the switch component, set this object to 
                   resetHardRestartOperation(2). This will toggle the reset line to the 
                   service processor causing it to re-initialize. The service processor on 
                   the component is directly reset, but the power state of the component 
                   will not be affected by this operation.

                   This object is intended to be write-only.

                   The component will experience a temporary loss of communication and the power 
                   state will change. Prior to executing this action, perform any operations needed
                   to protect user data.

                   Reading this object will always return the value of noOperation(0)."
                   ::= { smPowerServiceResetEntry 4 }

  -- ********************************************************************************
  -- Component Service Data params
  -- ********************************************************************************

    componentServiceData  OBJECT IDENTIFIER ::= { service 15 }

    componentServiceDataTable OBJECT-TYPE
                     SYNTAX  SEQUENCE OF ComponentServiceDataEntry
                     ACCESS  not-accessible
                     STATUS  mandatory
                     DESCRIPTION
                     "Table of component service data information."
                     ::= { componentServiceData 1 }

       componentServiceDataEntry OBJECT-TYPE
                     SYNTAX ComponentServiceDataEntry
                     ACCESS  not-accessible
                     STATUS  mandatory
                     DESCRIPTION
                     "Component service data entry"
                     INDEX { componentServiceDataTopologyPath }
                     ::= { componentServiceDataTable 1 }

       ComponentServiceDataEntry ::= SEQUENCE {
                   componentServiceDataTopologyPath OCTET STRING,
                   componentServiceDataComponentName OCTET STRING,
                   componentServiceDataDumpInitiate INTEGER,
                   componentServiceDataDumpRetrieve INTEGER,
                   componentServiceDataDumpCapabilityMask OCTET STRING,
                   componentServiceDataDumpInProgress INTEGER,
	           componentServiceDataStatus INTEGER,
		   componentServiceDataStatusDetails OCTET STRING
                   }

       componentServiceDataTopologyPath  OBJECT-TYPE
                   SYNTAX  OCTET STRING  (SIZE (0..100))
                   ACCESS  read-only
                   STATUS  mandatory
                   DESCRIPTION
                   "The unique identifier for a component in this table. The chassis and each
                    installed component is represented by a hardware topology tree, where
                    each node in the tree represents a component. The path to a particular
                    component consists of one or more <component>,<instance> pairs, where
                    each successive pair is a child of the previous parent pair.

                    As an example, the root of the tree is the chassis and is represented
                    by the pair 'CHASSIS, 1'. This pair indicates the first instance of
                    the chassis. If a blade is inserted in slot 4 of the chassis, its
                    topology path is 'CHASSIS, 1, BLADE, 4'. With this format, the
                    components in the chassis can be determined along with their relative
                    hierarchy to each other.

                    This component table is indexed by this unique topology
                    path and the numeric designations for the components are:

                     CHASSIS,                0x01   Chassis
                     MM,                     0x02   Management Module
                     BLADE,                  0x03   Main system board of a blade
                     POWER,                  0x04   Power Supply, Power Module, etc
                     COOLING,                0x05   Fan, blower, or other cooling device
                     IO_MODULE,              0x06   Has I/O interface, i.e. - switch or bridge
                     MEDIA,                  0x07   Media device
                     PROCESSOR,              0x08   Any processor, processor module, etc
                     STORAGE,                0x09   Any type of storage device
                     EXPANSION,              0x0A   Expansion Card (not covered by more specific type)
                     MEMORY,                 0x0B   Any memory device, module, etc
                     MFRU,                   0x0C   Managed FRU Device
                     PANEL,                  0x0D   Any sort of panel device, such as a front panel
                     BLADE_EXPANSION_MODULE, 0x0E   Expansion option (BEM) such as PEU, BSE, etc
                     CARD_EXPANSION,         0x0F   Expansion card, ie. daughter card
                     CARD_HS_EXPANSION,      0x10   High Speed Expansion card, ie. daughter card
                     INTERPOSER,             0x11   Interposer device
                     CLOCK,                  0x12   Clock card
                     MUX,                    0x13   Mulitplexer card
                     ADDIN,                  0x14   cKVM card & other addin cards
                     STORAGE_MODULE,         0x15   Container of one or more Storage Devices
                     SYS_EXPANSION_CARD,     0x16   Management card
                     BATTERY,                0x17   A single battery
                     BATTERY_MODULE,         0x18   Container of one or more batteries
                     REAR_LED,               0x19   Rear LED card
                     MEMORY_BANK,            0x1A   Memory banks
                     AIR_FILTER,             0x1B   Filter mechanism (bezel)
                     SERIAL_PORT_MODULE,     0x1C   Container of one or more serial ports
                     PARENT,                 0x1D   Reference to parent for multi-parent support
                     PHY_PORT,               0x1E   Physical port
                     IO_EXPANDER,            0x1F   RAID card
                     CABLE,                  0x20   Cable/Interconnect
                     FAN_MUX                 0x29   Fan multiplexer card
                     PCI_EXPRESS,            0x32   PCI express card on (PEN)
                     FLASH_DIMM,             0x33   Used for SPD devices that matches the silkscreen of the DIMM slot
                     RACK,                   0x50   Rack
                     PLATFORM,               0x51   Generic Platform like rack mounted server/appliance
                     DATAPLEX,               0x52   DataPlex
                     OTHER,                  0x53   Other unknown etc.
                     PERIPHERAL_MODULE,      0x54 
                     SYSTEM_BOARD,           0x55   System board
                     PROCESSOR_MODULE,       0x56 
                     BACK_PANEL,             0x57 
                     POWER_SYSTEM_BOARD,     0x58 
                     STORAGE_BACKPLANE,      0x59   Drive back plane
                     PROC_BOARD,             0x5A   Holds 1 or more processors
                     POWER_DI,               0x5B   Power mgt / power distribution board
                     CHASSIS_BACK_PANEL,     0x5C 
                     SUB_CHASSIS,            0x5D 
                     OTHER_CHASSIS_BOARD,    0x5E 
                     DEVICE_MODULE,          0x5F 
                     REMOTE_DEVICE,          0x60   Remote mgt communication device
                     EXTERNAL_ENVIRONMENT,   0x61   Such as external temp sensor for outside box temps
                     PROC_MEMORY_MODULE,     0x62   Processors and memory on same module"
                   ::= { componentServiceDataEntry 1 }

       componentServiceDataComponentName OBJECT-TYPE
                   SYNTAX  OCTET STRING
                   ACCESS  read-only
                   STATUS  mandatory
                   DESCRIPTION
                   "The name of the component as a null terminated string."
                   ::= { componentServiceDataEntry 2 }

       componentServiceDataDumpInitiate OBJECT-TYPE
                   SYNTAX  INTEGER {
                     processorDump(1),
                     platformDump(2),
                     partitionDump(3),
                     serviceData(4)
                   }
                   ACCESS  read-write
                   STATUS  mandatory
                   DESCRIPTION
                   "Initiates a type of dump collection to be initiated for the component and sent to the MM.

                   NOTE: Not all components support this, please check componentServiceDataDumpCapabilityMask
                   OID to see if the action is supported on this component. 

		   For switch modules the serviceData(4) is the only available value that can be set.

                   When the dump file is created, the node transfers it to the /tftproot/service directory 
                   on the CMM. Only one file can be moved to this directory at a time, so please use the fileManagement 
                   MIB information to check if the file has been completed.

                   NOTE: Value returned for the GET command is meaningless
                   for this MIB object."
                   ::= { componentServiceDataEntry 3 }

       componentServiceDataDumpRetrieve OBJECT-TYPE
                   SYNTAX INTEGER {
                     processorDump(1),
                     platformDump(2),
                     partitionDump(3),
                     serviceData(4)
                   }
                   ACCESS read-write
                   STATUS mandatory
                   DESCRIPTION
                   "Retrieve a type of service data file from component to MM.

                   NOTE: This OID only is valid for the last four bit mask designations listed
                   in the componentServiceDataDumpCapabilityMask OID. 

					NOTE: This OID is not used for switch modules.

                   The dump file is transfered to the /tftproot/service directory 
                   on the CMM. Only one file can be moved to this directory at a time, 
                   so please use the fileManagement MIB information to check if the file has been completed.

                   NOTE: Value returned for the GET command is meaningless
                   for this MIB object."
                   ::= { componentServiceDataEntry 4 }

       componentServiceDataDumpCapabilityMask OBJECT-TYPE
                   SYNTAX  OCTET STRING
                   ACCESS  read-only
                   STATUS  mandatory
                   DESCRIPTION
                   "Indicates whether the component has the capability to trigger service data and if so,
                   which operations are supported and whether the file can be transferred to the MM
                   from the component.
                   The values and meanings are as follows:
                   0000 0000 means this component does not support any at all.

                   0000 0001 means this component supports 'processor' type and the file remains on the component.
                   0000 0010 means this component supports 'platform' type and the file remains on the component.
                   0000 0100 means this component supports 'partition' type and the file remians on the component.

                   0000 1000 means this component supports 'processor' type and the file can be transferred to the MM.
                   0001 0000 means this component supports 'platform' type and the file can be transferred to the MM.
                   0010 0000 means this component supports 'partition' type and the file can be transferred to the MM
                   0100 0000 means this component supports 'serviceData' type and the file can be transferred to the MM
                   For example, the returned value of 01111000 means this component supports 'processor','platform',
                   'partition' and 'serviceData' types, and the file can be transferred to the MM"
                   ::= { componentServiceDataEntry 5 }

       componentServiceDataDumpInProgress OBJECT-TYPE
                   SYNTAX INTEGER {
                     inProgress(1),
                     notInProgress(2),
                     unknown(255)
                   }
                   ACCESS read-only
                   STATUS mandatory
                   DESCRIPTION
                   "An indicator as to whether a component dump is in progress for the specified component.
                    This object ONLY applies to dumps that can be triggered by the MM and where the
                    dump file is transferred to the MM filesystem upon completion. See the
                    componentServiceDataDumpCapabilityMask object for support levels. The flag that this MIB object
                    represents will be set on when the IPMI command is sent to the component indicating 'init dump'
                    and will be cleared upon receiving the valid dump file from the component or the
                    creation of the text file indicating the problem encountered.
                    If it cannot be determined if the dump is in progress, the unknown(255) value is returned."
                   ::= { componentServiceDataEntry 6}
	componentServiceDataStatus OBJECT-TYPE
		  SYNTAX INTEGER
		  ACCESS read-only
		  STATUS mandatory
		  DESCRIPTION
		  "A status indicator for dump progress. This object ONLY applies to switch modules dumps."
		  ::= { componentServiceDataEntry 7}

	componentServiceDataStatusDetails OBJECT-TYPE
		  SYNTAX OCTET STRING
		  ACCESS read-only
		  STATUS mandatory
		  DESCRIPTION
		  "The failure status as a null terminated string. This object ONLY applies to switch modules dumps."
		  ::= { componentServiceDataEntry 8}


      -- *************************************************************************
      -- componentServiceDataTableCacheTimeout
      -- *************************************************************************
      componentServiceDataTableCacheTimeout OBJECT-TYPE
               SYNTAX  INTEGER
               ACCESS  read-only
               STATUS  mandatory
               DESCRIPTION
               "The timeout value (in seconds) of the cached data for the
               table, componentServiceDataTable.
               This value is static (constant) and cannot be set."
               ::= { componentServiceData 2 }


  -- ********************************************************************************
  -- FFDC Service Data Generation and Download
  -- ********************************************************************************
    downloadMMServiceData  OBJECT IDENTIFIER ::= { service 21 }

      downloadMMServiceDataFileCreateAndDownload OBJECT-TYPE
              SYNTAX  OCTET STRING (SIZE(0..512))
              ACCESS  read-write
              STATUS  mandatory
              DESCRIPTION
              "Specifying this string initiates the generation of the FFDC
              (First-Failure Data Capture) data collection (compressed
              group of files) for the CMM and the download of this file to the
              specified destination.

              The destination is a string of chars that specifies the
              remote location of service data to be saved.  Use one of the
              following protocols:  sftp, tftp, ftp, http or https.
              An example of a qualified location can be:
              <protocol>://[<user>[:password][;fingerprint=<host>]@]<host>
              [:<port>]/<path>/<to>/<file>

              Note:  It is recommended that the saved-data filename have an
              extension of .tgz to allow support personnel to identify the file.

              Reading this string will always return 'Not readable' since
              this string may contain a password."
              ::= { downloadMMServiceData 1 }


      downloadMMServiceDataStatus OBJECT-TYPE
              SYNTAX INTEGER {
                  ready(0),
                  fileGenerationInProgress(1),
                  fileDownloadInProgress(2),
                  cancelingDownload(3)
              }
              ACCESS read-only
              STATUS mandatory
              DESCRIPTION
              "An indicator as to whether the FFDC generation and download
              is in progress.  To initiate this process, set the object,
              downloadMMServiceDataFileCreateAndDownload (see the
              object's description for details)."
              ::= { downloadMMServiceData 2}


      downloadMMServiceDataResult OBJECT-TYPE
              SYNTAX INTEGER {
                  none(0),
                  permissionFailed(1),
                  fileGenerationFailed(2),
                  fileDownloadFailed(3),
                  canceled(4),
                  complete(5)
              }
              ACCESS read-write
              STATUS mandatory
              DESCRIPTION
              "An indicator as to whether the FFDC generation and download
              was successful.

              The FFDC generation and download is started by setting a
              destination filename with the object,
              downloadMMServiceDataFileCreateAndDownload.

              If the FFDC file generation and download process completes
              successfully, this object is set to complete(5).

              If the process encounters an error, this object is set to
              either: permissionFailed(1), fileGenerationFailed(2) or
              fileDownloadFailed(3).

              If the process is canceled by the user, this object will be set
              to canceled(4).

              A value of none(0) is the default value.  This object may be
              set to none(0) if the object, downloadMMServiceDataStatus,
              has a value of ready(0).  Setting this object to any value other
              than none(0) will report an error."
              ::= { downloadMMServiceData 3}


      downloadMMServiceDataCancelDownload OBJECT-TYPE
              SYNTAX INTEGER {
                  none(0),
                  cancel(1)
              }
              ACCESS read-write
              STATUS mandatory
              DESCRIPTION
              "Set this object to 'cancel(1)' to stop the FFDC file download
              process.  'cancel(1)' is the only valid value that may be set.

              The value of this object will be 'cancel(1)' if an user has
              set this value and an active FFDC download is in progress. After
              the process has been canceled, this object will automatically
              be set to 'none(0)'."
              ::= { downloadMMServiceData 4}


      -- *************************************************************************
      -- Scalable Complex Information
      -- *************************************************************************

      scalableComplexTable OBJECT-TYPE
                  SYNTAX  SEQUENCE OF ScalableComplexEntry
                  ACCESS  not-accessible
                  STATUS  mandatory
                  DESCRIPTION
                    "Table of scalable complex information. This table provides information
                     related to the scalable complexes installed in the chassis."
                  ::= { scaling 1 }

      scalableComplexEntry OBJECT-TYPE
                  SYNTAX ScalableComplexEntry
                  ACCESS  not-accessible
                  STATUS  mandatory
                  DESCRIPTION
                    "Scalable complex information."
                  INDEX { scalableComplexTopologyPath }
                  ::= { scalableComplexTable 1 }

      ScalableComplexEntry ::= SEQUENCE {
                  scalableComplexTopologyPath      OCTET STRING,
                  scalableComplexIdentifier        INTEGER,
                  scalableComplexNodeName          OCTET STRING,
                  scalableComplexNodeHealthState   INTEGER,
                  scalableComplexNodePowerState    INTEGER,
                  scalableComplexNodeResources     OCTET STRING
                  }

        scalableComplexTopologyPath  OBJECT-TYPE
                   SYNTAX  OCTET STRING  (SIZE (0..100))
                   ACCESS  read-only
                   STATUS  mandatory
                   DESCRIPTION
                   "The unique identifier for a component in this table. The chassis and each
                    installed component is represented by a hardware topology tree, where
                    each node in the tree represents a component. The path to a particular
                    component consists of one or more <component>,<instance> pairs, where
                    each successive pair is a child of the previous parent pair.

                    As an example, the root of the tree is the chassis and is represented
                    by the pair 'CHASSIS, 1'. This pair indicates the first instance of
                    the chassis. If a blade is inserted in slot 4 of the chassis, its
                    topology path is 'CHASSIS, 1, BLADE, 4'. With this format, the
                    components in the chassis can be determined along with their relative
                    hierarchy to each other.

                    This component table is indexed by this unique topology
                    path and the numeric designations for the components are:

                     CHASSIS,                0x01   Chassis
                     MM,                     0x02   Management Module
                     BLADE,                  0x03   Main system board of a blade
                     POWER,                  0x04   Power Supply, Power Module, etc
                     COOLING,                0x05   Fan, blower, or other cooling device
                     IO_MODULE,              0x06   Has I/O interface, i.e. - switch or bridge
                     MEDIA,                  0x07   Media device
                     PROCESSOR,              0x08   Any processor, processor module, etc
                     STORAGE,                0x09   Any type of storage device
                     EXPANSION,              0x0A   Expansion Card (not covered by more specific type)
                     MEMORY,                 0x0B   Any memory device, module, etc
                     MFRU,                   0x0C   Managed FRU Device
                     PANEL,                  0x0D   Any sort of panel device, such as a front panel
                     BLADE_EXPANSION_MODULE, 0x0E   Expansion option (BEM) such as PEU, BSE, etc
                     CARD_EXPANSION,         0x0F   Expansion card, ie. daughter card
                     CARD_HS_EXPANSION,      0x10   High Speed Expansion card, ie. daughter card
                     INTERPOSER,             0x11   Interposer device
                     CLOCK,                  0x12   Clock card
                     MUX,                    0x13   Mulitplexer card
                     ADDIN,                  0x14   cKVM card & other addin cards
                     STORAGE_MODULE,         0x15   Container of one or more Storage Devices
                     SYS_EXPANSION_CARD,     0x16   Management card
                     BATTERY,                0x17   A single battery
                     BATTERY_MODULE,         0x18   Container of one or more batteries
                     REAR_LED,               0x19   Rear LED card
                     MEMORY_BANK,            0x1A   Memory banks
                     AIR_FILTER,             0x1B   Filter mechanism (bezel)
                     SERIAL_PORT_MODULE,     0x1C   Container of one or more serial ports
                     PARENT,                 0x1D   Reference to parent for multi-parent support
                     PHY_PORT,               0x1E   Physical port
                     IO_EXPANDER,            0x1F   RAID card
                     CABLE,                  0x20   Cable/Interconnect
                     FAN_MUX                 0x29   Fan multiplexer card
                     PCI_EXPRESS,            0x32   PCI express card on (PEN)
                     FLASH_DIMM,             0x33   Used for SPD devices that matches the silkscreen of the DIMM slot
                     RACK,                   0x50   Rack
                     PLATFORM,               0x51   Generic Platform like rack mounted server/appliance
                     DATAPLEX,               0x52   DataPlex
                     OTHER,                  0x53   Other unknown etc.
                     PERIPHERAL_MODULE,      0x54 
                     SYSTEM_BOARD,           0x55   System board
                     PROCESSOR_MODULE,       0x56 
                     BACK_PANEL,             0x57 
                     POWER_SYSTEM_BOARD,     0x58 
                     STORAGE_BACKPLANE,      0x59   Drive back plane
                     PROC_BOARD,             0x5A   Holds 1 or more processors
                     POWER_DI,               0x5B   Power mgt / power distribution board
                     CHASSIS_BACK_PANEL,     0x5C 
                     SUB_CHASSIS,            0x5D 
                     OTHER_CHASSIS_BOARD,    0x5E 
                     DEVICE_MODULE,          0x5F 
                     REMOTE_DEVICE,          0x60   Remote mgt communication device
                     EXTERNAL_ENVIRONMENT,   0x61   Such as external temp sensor for outside box temps
                     PROC_MEMORY_MODULE,     0x62   Processors and memory on same module"
                   ::= { scalableComplexEntry 1 }

      scalableComplexIdentifier  OBJECT-TYPE
                  SYNTAX  INTEGER
                  ACCESS  read-only
                  STATUS  mandatory
                  DESCRIPTION
                    "The unique numeric identifier for a complex installed in the chassis."
                  ::= { scalableComplexEntry 2 }

      scalableComplexNodeName OBJECT-TYPE
                   SYNTAX  OCTET STRING
                   ACCESS  read-only
                   STATUS  mandatory
                   DESCRIPTION
                   "The name of the node as a null terminated string."
                   ::= { scalableComplexEntry 3 }

      scalableComplexNodeHealthState  OBJECT-TYPE
                   SYNTAX  INTEGER {
                     unknown(0),
                     good(1),
                     warning(2),
                     critical(3),
                     kernelMode(4),
                     discovering(5),
                     commError(6),
                     noPower(7),
                     flashing(8),
                     initFailure(9),
                     insufficientPower(10),
                     powerDenied(11),
                     maintMode(12),
                     firehoseDump(13)
                   }
                   ACCESS  read-only
                   STATUS  mandatory
                   DESCRIPTION
                   "The system health state for the component.

                    Unknown: Component is in an undefined state.
                    Good: Component is operating normally.
                    Warning: One or more outstanding warnings exist for this component.
                    Critical: One or more outstanding critical events for this component.
                    Kernel Mode: Component is in kernel mode.
                    Discovering: The MM is currently in the process of discovering this component.
                    Communications Error: The MM failed to communicate with this component.
                    No Power: No power to the component's domain.
                    Flashing: Flashing in progress.
                    Initialization Failure: Component failed to initialized.
                    Insufficient Power: Not enough power is left in the component's domain to power the component.
                    Power Denied: Power was denied to the component.
                    Maintenance Mode: Node is undergoing a service operation and should not be updated or powered on/off.
                    Firehose Dump: Node is undergoing a storage save operation and should not be udpated or powered on/off"
                   ::= { scalableComplexEntry 4 }

      scalableComplexNodePowerState  OBJECT-TYPE
                   SYNTAX  INTEGER {
                     off(0),
                     on(1),
                     standby(3),
                     hibernate(4)
                   }
                   ACCESS  read-only
                   STATUS  mandatory
                   DESCRIPTION
                   "Indicates the power state of the node."
                   ::= { scalableComplexEntry 5 }

      scalableComplexNodeResources OBJECT-TYPE
                   SYNTAX  OCTET STRING
                   ACCESS  read-only
                   STATUS  mandatory
                   DESCRIPTION
                    "A string providing a summary overview of the resources provided by this node."
                   ::= { scalableComplexEntry 6 }

     -- *************************************************************************
     -- Telco Management 
     -- *************************************************************************

     -- ***********************************************************************
     -- Telco Chassis LEDs
     -- ***********************************************************************
     telcoChassisLEDs OBJECT IDENTIFIER ::= { telcoManagement 1 }

     telcoCriticalLED   OBJECT-TYPE
                   SYNTAX INTEGER {
                     off(0),
                     on(1)
                   }
                   ACCESS  read-only
                   STATUS  mandatory
                   DESCRIPTION
                   "Indicates whether the telco CRT (Critical) LED is on or off."
                   ::= { telcoChassisLEDs 1 }


     telcoMajorLED      OBJECT-TYPE
                   SYNTAX INTEGER {
                     off(0),
                     on(1)
                   }
                   ACCESS  read-only
                   STATUS  mandatory
                   DESCRIPTION
                   "Indicates whether the telco MJR (Major) LED is on or off."
                   ::= { telcoChassisLEDs 2 }

     telcoMinorLED      OBJECT-TYPE
                   SYNTAX INTEGER {
                     off(0),
                     on(1)
                   }
                   ACCESS  read-only
                   STATUS  mandatory
                   DESCRIPTION
                   "Indicates whether the telco MNR (Minor) LED is on or off."
                   ::= { telcoChassisLEDs 3 }

     -- ***********************************************************************
     -- Telco Chassis Environmentals
     -- ***********************************************************************
     telcoChassisEnv OBJECT IDENTIFIER ::= { telcoManagement 2 }

     telcoNEBSCoolingOverride   OBJECT-TYPE
                   SYNTAX INTEGER {
                     off(0),
                     on(1)
                   }
                   ACCESS  read-write
                   STATUS  mandatory
                   DESCRIPTION
                   "Enabling the NEBS Cooling Mode Override will immediately disable 
                    the Acoustic Attenuation Mode.Both modified settings will be saved 
                    in the system configuration and forwarded to all nodes and the standby 
                    CMM. Also the current chassis ambient temperature threshold will be 
                    reloaded and monitored with the new NEBS-defined threshold." 
                   ::= { telcoChassisEnv 1 }

     -- ************************************************************************
     -- Telco System Health
     -- ************************************************************************
     telcoSystemHealth OBJECT IDENTIFIER ::= { telcoManagement 3 }

     -- ************************************************************************
     -- Telco Overall System Health Status
     -- ************************************************************************
     telcoSystemHealthStatus  OBJECT-TYPE
                   SYNTAX  INTEGER {
                                     none(0),
                                     info(2),
                                     minor(4),
                                     major(5),
                                     critical(6)
                                   }
                   ACCESS  read-only
                   STATUS  mandatory
                   DESCRIPTION
                   "Indicates overall status of system health for the system in which the 
                    CMM resides. Value of 'critical' indicates a non-recoverable 
                    service affecting condition has occurred that requires an 
                    immediate action. A value of 'major' indicates a critical 
                    service affecting condition has occurred that requires an urgent
                    action. A value of 'minor' indicates a non-service affecting 
                    condition has occurred. Corrective action should be taken in 
                    order to prevent a more serious fault. A value of 'none' 
                    indicates that the system is operating normally."
                   ::= { telcoSystemHealth 1 }

     -- ************************************************************************
     -- TelcoSystem Health Summary
     -- ************************************************************************
     telcoSystemHealthSummaryTable OBJECT-TYPE
                   SYNTAX  SEQUENCE OF TelcoSystemHealthSummaryEntry
                   ACCESS  not-accessible
                   STATUS  mandatory
                   DESCRIPTION
                   "Table of alarms raised for this system. Contains more detailed
                   information about the reasons for the overall system
                   health status." 
                   ::= { telcoSystemHealth 2 }

     telcoSystemHealthSummaryEntry OBJECT-TYPE
                   SYNTAX TelcoSystemHealthSummaryEntry
                   ACCESS  not-accessible
                   STATUS  mandatory
                   DESCRIPTION
                   "Telco System Health Summary entry."
                   INDEX { telcoSystemHealthSummaryTopologyPath, telcoSystemHealthSummaryIndex }
                   ::= { telcoSystemHealthSummaryTable 1 }

     TelcoSystemHealthSummaryEntry ::= SEQUENCE {
                   telcoSystemHealthSummaryTopologyPath OCTET STRING,
                   telcoSystemHealthSummaryIndex INTEGER,
                   telcoSystemHealthSummaryName OCTET STRING,
                   telcoSystemHealthSummarySeverity INTEGER,
                   telcoSystemHealthSummaryDescription OCTET STRING,
                   telcoSystemHealthSummaryEventID INTEGER,
                   telcoSystemHealthSummaryAlarmID OCTET STRING,
                   telcoSystemHealthSummaryAcknowledge INTEGER,
                   telcoSystemHealthSummaryAssertTime OCTET STRING,
                   telcoSystemHealthSummaryCommonEventID OCTET STRING
                   }

      telcoSystemHealthSummaryTopologyPath  OBJECT-TYPE
                   SYNTAX  OCTET STRING  (SIZE (0..100))
                   ACCESS  read-only
                   STATUS  mandatory
                   DESCRIPTION
                   "The unique identifier for a component in this table. The chassis and each
                    installed component is represented by a hardware topology tree, where
                    each node in the tree represents a component. The path to a particular
                    component consists of one or more <component>,<instance> pairs, where
                    each successive pair is a child of the previous parent pair.

                    As an example, the root of the tree is the chassis and is represented
                    by the pair 'CHASSIS, 1'. This pair indicates the first instance of
                    the chassis. If a blade is inserted in slot 4 of the chassis, its
                    topology path is 'CHASSIS, 1, BLADE, 4'. With this format, the
                    components in the chassis can be determined along with their relative
                    hierarchy to each other.

                    Note that this TP is preceded by a single octet that specifies the TP length.
                    This is required since this table is indexed with two indices and, therefore,
                    the TP length must be explicitly provided.

                    This component table is indexed by this unique topology
                    path and the numeric designations for the components are:

                     CHASSIS,                0x01   Chassis
                     MM,                     0x02   Management Module
                     BLADE,                  0x03   Main system board of a blade
                     POWER,                  0x04   Power Supply, Power Module, etc
                     COOLING,                0x05   Fan, blower, or other cooling device
                     IO_MODULE,              0x06   Has I/O interface, i.e. - switch or bridge
                     MEDIA,                  0x07   Media device
                     PROCESSOR,              0x08   Any processor, processor module, etc
                     STORAGE,                0x09   Any type of storage device
                     EXPANSION,              0x0A   Expansion Card (not covered by more specific type)
                     MEMORY,                 0x0B   Any memory device, module, etc
                     MFRU,                   0x0C   Managed FRU Device
                     PANEL,                  0x0D   Any sort of panel device, such as a front panel
                     BLADE_EXPANSION_MODULE, 0x0E   Expansion option (BEM) such as PEU, BSE, etc
                     CARD_EXPANSION,         0x0F   Expansion card, ie. daughter card
                     CARD_HS_EXPANSION,      0x10   High Speed Expansion card, ie. daughter card
                     INTERPOSER,             0x11   Interposer device
                     CLOCK,                  0x12   Clock card
                     MUX,                    0x13   Mulitplexer card
                     ADDIN,                  0x14   cKVM card & other addin cards
                     STORAGE_MODULE,         0x15   Container of one or more Storage Devices
                     SYS_EXPANSION_CARD,     0x16   Management card
                     BATTERY,                0x17   A single battery
                     BATTERY_MODULE,         0x18   Container of one or more batteries
                     REAR_LED,               0x19   Rear LED card
                     MEMORY_BANK,            0x1A   Memory banks
                     AIR_FILTER,             0x1B   Filter mechanism (bezel)
                     SERIAL_PORT_MODULE,     0x1C   Container of one or more serial ports
                     PARENT,                 0x1D   Reference to parent for multi-parent support
                     PHY_PORT,               0x1E   Physical port
                     IO_EXPANDER,            0x1F   RAID card
                     CABLE,                  0x20   Cable/Interconnect
                     FAN_MUX                 0x29   Fan multiplexer card
                     PCI_EXPRESS,            0x32   PCI express card on (PEN)
                     FLASH_DIMM,             0x33   Used for SPD devices that matches the silkscreen of the DIMM slot
                     RACK,                   0x50   Rack
                     PLATFORM,               0x51   Generic Platform like rack mounted server/appliance
                     DATAPLEX,               0x52   DataPlex
                     OTHER,                  0x53   Other unknown etc.
                     PERIPHERAL_MODULE,      0x54 
                     SYSTEM_BOARD,           0x55   System board
                     PROCESSOR_MODULE,       0x56 
                     BACK_PANEL,             0x57 
                     POWER_SYSTEM_BOARD,     0x58 
                     STORAGE_BACKPLANE,      0x59   Drive back plane
                     PROC_BOARD,             0x5A   Holds 1 or more processors
                     POWER_DI,               0x5B   Power mgt / power distribution board
                     CHASSIS_BACK_PANEL,     0x5C 
                     SUB_CHASSIS,            0x5D 
                     OTHER_CHASSIS_BOARD,    0x5E 
                     DEVICE_MODULE,          0x5F 
                     REMOTE_DEVICE,          0x60   Remote mgt communication device
                     EXTERNAL_ENVIRONMENT,   0x61   Such as external temp sensor for outside box temps
                     PROC_MEMORY_MODULE,     0x62   Processors and memory on same module"
                   ::= { telcoSystemHealthSummaryEntry 1 }

     telcoSystemHealthSummaryIndex  OBJECT-TYPE
                   SYNTAX  INTEGER
                   ACCESS  read-only
                   STATUS  mandatory
                   DESCRIPTION
                   "Telco System Health Summary table row index."
                   ::= { telcoSystemHealthSummaryEntry 2 }

     telcoSystemHealthSummaryName  OBJECT-TYPE
                   SYNTAX  OCTET STRING
                   ACCESS  read-only
                   STATUS  mandatory
                   DESCRIPTION
                   "The name of the component as a null terminated string for the associated alarm."
                   ::= { telcoSystemHealthSummaryEntry 3 }

     telcoSystemHealthSummarySeverity  OBJECT-TYPE
                   SYNTAX  INTEGER {
                                     none(0),
                                     info(2),
                                     minor(4),
                                     major(5),
                                     critical(6)
                                   }
                   ACCESS  read-only
                   STATUS  mandatory
                   DESCRIPTION
                   "The severity of a specific alarm raised on the telco chassis.  
                    A value of 'critical' indicates a non-recoverable 
                    service affecting condition has occurred that requires an 
                    immediate action. A value of 'major' indicates a critical 
                    service affecting condition has occurred that requires an urgent
                    action. A value of 'minor' indicates a non-service affecting 
                    condition has occurred. Corrective action should be taken in 
                    order to prevent a more serious fault. A value of 'none' 
                    indicates that the system is operating normally."
                   ::= { telcoSystemHealthSummaryEntry 4 }

     telcoSystemHealthSummaryDescription  OBJECT-TYPE
                   SYNTAX  OCTET STRING
                   ACCESS  read-only
                   STATUS  mandatory
                   DESCRIPTION
                   "The alarm description text."
                   ::= { telcoSystemHealthSummaryEntry 5 }
                 
     telcoSystemHealthSummaryEventID  OBJECT-TYPE
                   SYNTAX INTEGER 
                   ACCESS  read-only
                   STATUS  mandatory
                   DESCRIPTION
                   "The 4 byte event ID for the problem that was logged in the CMM event log."
                   ::= { telcoSystemHealthSummaryEntry 6 }
       
     telcoSystemHealthSummaryAlarmID  OBJECT-TYPE
                   SYNTAX OCTET STRING 
                   ACCESS  read-only
                   STATUS  mandatory
                   DESCRIPTION
                   "The alarm identifier that is unique for all alarms."
                   ::= { telcoSystemHealthSummaryEntry 7 }
     
     telcoSystemHealthSummaryAcknowledge  OBJECT-TYPE
                   SYNTAX INTEGER {
                     unacknowledged(0),
                     acknowledged(1)
                   }
                   ACCESS  read-only
                   STATUS  mandatory
                   DESCRIPTION
                   "Indicates whether the alarm has been acknowledged or unacknowledged."
                   ::= { telcoSystemHealthSummaryEntry 8 }
    
     telcoSystemHealthSummaryAssertTime  OBJECT-TYPE
                   SYNTAX  OCTET STRING
                   ACCESS  read-only
                   STATUS  mandatory
                   DESCRIPTION
                   "The date and time the alarm was raised."
                   ::= { telcoSystemHealthSummaryEntry 9 }

     telcoSystemHealthSummaryCommonEventID  OBJECT-TYPE
                   SYNTAX  OCTET STRING
                   ACCESS  read-only
                   STATUS  mandatory
                   DESCRIPTION
                   "The Common Event ID for the problem that was logged in the CMM event log.."
                   ::= { telcoSystemHealthSummaryEntry 10 }


     -- ************************************************************************
     -- Telco Alarm Management 
     -- ************************************************************************
     telcoAlarmMgmt OBJECT IDENTIFIER ::= { telcoManagement 4 }

     -- ************************************************************************
     -- Telco Create a Software Alarm
     -- ************************************************************************
     telcoAlarmCreate OBJECT-TYPE
                   SYNTAX  OCTET STRING 
                   ACCESS  read-write
                   STATUS  mandatory
                   DESCRIPTION
                   "Create a software alarm. An input octet string must be provided 
                    in this format:
                     
                     - Alarm severity level (CRT, MJR, MNR)
                     - A colon seperator 
                     - The alarm description (64 bytes max, including the NULL terminator).

                   An example format is 'MNR:Power supply 2 has a broken handle.' 
                        
                   NOTE 1: Value returned for the GET command is meaningless for 
                   this MIB object."
                   ::= { telcoAlarmMgmt 1 }

     -- ************************************************************************
     -- Telco Ack an Alarm
     -- ************************************************************************
     telcoAlarmAck OBJECT-TYPE
                   SYNTAX  OCTET STRING 
                   ACCESS  read-write
                   STATUS  mandatory
                   DESCRIPTION
                   "Acknowledge an alarm. An input octet string consists of the 
                   alarm ID as defined in the telcoSystemHealthSummaryAlarmID
                   object.    
                          
                   NOTE 1: Value returned for the GET command is meaningless for 
                   this MIB object."
                   ::= { telcoAlarmMgmt 2 }

     -- ************************************************************************
     -- Telco Clear an Alarm
     -- ************************************************************************
     telcoAlarmClear OBJECT-TYPE
                   SYNTAX  OCTET STRING 
                   ACCESS  read-write
                   STATUS  mandatory
                   DESCRIPTION
                   "Clear an active alarm. An input octet string consists of the 
                   alarm ID as defined in the telcoSystemHealthSummaryAlarmID
                   object.  
                          
                   NOTE1 : Value returned for the GET command is meaningless for 
                   this MIB object."
                   ::= { telcoAlarmMgmt 3 }

END
